STRATAON-MIB DEFINITIONS ::= BEGIN

IMPORTS
    MODULE-IDENTITY,
    OBJECT-IDENTITY,
    OBJECT-TYPE,
    enterprises,
    Integer32,
    Gauge32,
    TimeTicks
        FROM SNMPv2-SMI
    DisplayString,
    TEXTUAL-CONVENTION
        FROM SNMPv2-TC
    MODULE-COMPLIANCE,
    OBJECT-GROUP
        FROM SNMPv2-CONF;

strataonMIB MODULE-IDENTITY
    LAST-UPDATED "202609111235Z"
    ORGANIZATION "STRATAON Equipamentos Eletronicos Ltda."
    CONTACT-INFO
        "STRATAON
         Web: https://strataon.com.br
         E-mail: suporte@strataon.com.br"
    DESCRIPTION
        "STRATAON enterprise MIB using the official IANA Private Enterprise Number 66204.

         This MIB contains common STRATAON objects and product-specific branches
         for current and future STRATAON products. Current product IDs are:
         1 = miniPLC, 2 = smartPDU, 3 = miniENV, 4 = sentiaMAN, 5 = sentiaPRO,
         6 = sentiaLOK."
    REVISION "202609111235Z"
    DESCRIPTION
        "Version 1.8. Added sentiaLOK product branch at .10.6. The sentiaLOK
         exposes 32 subordinate station slots. Each station provides node, name,
         communication status, firmware, device type, eight digital inputs and
         eight digital outputs. Station attributes use subidentifiers 101 through
         132. Product ID 6 is assigned to sentiaLOK."
    REVISION "202608162321Z"
    DESCRIPTION
        "Version 1.7. Added sentiaPRO product branch at .10.5. The sentiaPRO
         exposes one set of product-specific environmental and access state
         objects: three temperatures, one humidity value, alarm state, two
         lock states and two door states. Temperature and humidity values use
         scale x10. Product ID 5 is assigned to sentiaPRO."
    REVISION "202608162100Z"
    DESCRIPTION
        "Version 1.6. Added sentiaMAN product branch at .10.4. The sentiaMAN
         exposes a fixed count of subordinate station slots and 13 station
         attribute branches using subidentifiers 101 through 132. Attributes
         include node number, station name, communication status, firmware,
         three temperatures, humidity, alarm state, two lock states and two
         door states. Temperature and humidity values use scale x10."
    REVISION "202608112114Z"
    DESCRIPTION
        "Version 1.5. Corrected miniENV environmental measurement units.
         Humidity inputs HUM01 and HUM02 are represented as percent RH x10.
         CO2 input CO201 is represented directly in ppm, without x10 scaling.
         No object identifiers were changed."
    REVISION "202607311241Z"
    DESCRIPTION
        "Version 1.4. Publication release consolidating the validated
         STRATAON MIB definitions for miniPLC, smartPDU and miniENV.
         No object identifiers or object semantics were changed from
         version 1.3.4."
    REVISION "202607311130Z"
    DESCRIPTION
        "Version 1.3.4. Reorganized only the smartPDU relay OIDs.
         Relay count remains at subidentifier 1, relay states now use
         subidentifiers 101 through 108, and persistent relay activation
         counters also use subidentifiers 101 through 108."
    REVISION "202607311100Z"
    DESCRIPTION
        "Version 1.3.3. Reorganized only the miniPLC product variable OIDs.
         Count objects remain at subidentifier 1 and DI, DO, BOOL and LONG
         variables now use subidentifiers 101 through 132, preserving
         natural channel ordering in SNMP monitoring tools."
    REVISION "202607310953Z"
    DESCRIPTION
        "Version 1.3.1. Reorganized miniENV product variable OIDs so that
         count remains at subidentifier 1 and variables use subidentifiers
         101 onward. This preserves natural channel ordering in SNMP
         monitoring tools such as PRTG."
    REVISION "202607301900Z"
    DESCRIPTION
        "Version 1.3. Added the miniENV product branch at .10.3 with
         9 digital inputs, 2 digital outputs, 32 boolean variables,
         32 signed long variables, 5 temperature values, 2 humidity
         values and 1 CO2 value. Environmental values use scale x10."
    REVISION "202607250000Z"
    DESCRIPTION
        "Added eight persistent smartPDU relay activation counters under
         smartPDU relay statistics at .10.2.2."
    REVISION "202607091230Z"
    DESCRIPTION
        "Refined miniPLC boolean branch naming and added StrataonBinaryState
         textual convention for binary state objects."
    REVISION "202607091205Z"
    DESCRIPTION
        "Aligned product branches with firmware layout:
         common system at .1, common network at .2, products at .10,
         miniPLC at .10.1 and smartPDU at .10.2. Count objects are
         first in each product group and variables start at subidentifier 2."
    REVISION "202607090900Z"
    DESCRIPTION
        "Updated the enterprise root to the official IANA Private Enterprise Number 66204."
    REVISION "202607070100Z"
    DESCRIPTION
        "Adjusted count objects to avoid using zero as the last subidentifier of OBJECT-TYPE definitions."
    REVISION "202607070000Z"
    DESCRIPTION
        "Initial STRATAON MIB with common system/network groups,
         miniPLC product branch and smartPDU product branch."
    ::= { enterprises 66204 }

-- =============================================================
-- Textual conventions
-- =============================================================

StrataonBinaryState ::= TEXTUAL-CONVENTION
    STATUS current
    DESCRIPTION
        "Generic binary state used by STRATAON objects.
         off(0) means disabled, inactive or de-energized.
         on(1) means enabled, active or energized.
         The exact physical meaning depends on the object description."
    SYNTAX INTEGER {
        off(0),
        on(1)
    }

-- =============================================================
-- Root branches
-- =============================================================

strataonSystem OBJECT-IDENTITY
    STATUS current
    DESCRIPTION "Common system information for STRATAON devices."
    ::= { strataonMIB 1 }

strataonNetwork OBJECT-IDENTITY
    STATUS current
    DESCRIPTION "Common network information for STRATAON devices."
    ::= { strataonMIB 2 }

strataonProducts OBJECT-IDENTITY
    STATUS current
    DESCRIPTION "STRATAON product-specific branches."
    ::= { strataonMIB 10 }

strataonNotifications OBJECT-IDENTITY
    STATUS current
    DESCRIPTION "Reserved branch for future SNMP notifications/traps."
    ::= { strataonMIB 20 }

strataonConformance OBJECT-IDENTITY
    STATUS current
    DESCRIPTION "Conformance statements for STRATAON MIB."
    ::= { strataonMIB 30 }

-- =============================================================
-- Common system group: 1.3.6.1.4.1.66204.1
-- =============================================================

strataonProductId OBJECT-TYPE
    SYNTAX Integer32
    MAX-ACCESS read-only
    STATUS current
    DESCRIPTION
        "STRATAON product ID. miniPLC=1, smartPDU=2, miniENV=3, sentiaMAN=4, sentiaPRO=5, sentiaLOK=6."
    ::= { strataonSystem 1 }

strataonUptime OBJECT-TYPE
    SYNTAX TimeTicks
    MAX-ACCESS read-only
    STATUS current
    DESCRIPTION
        "Device uptime in hundredths of seconds."
    ::= { strataonSystem 2 }

strataonHeapFree OBJECT-TYPE
    SYNTAX Gauge32
    UNITS "bytes"
    MAX-ACCESS read-only
    STATUS current
    DESCRIPTION
        "Current free heap memory."
    ::= { strataonSystem 3 }

strataonHeapMinimum OBJECT-TYPE
    SYNTAX Gauge32
    UNITS "bytes"
    MAX-ACCESS read-only
    STATUS current
    DESCRIPTION
        "Minimum free heap memory since boot."
    ::= { strataonSystem 4 }

strataonResetReason OBJECT-TYPE
    SYNTAX Integer32
    MAX-ACCESS read-only
    STATUS current
    DESCRIPTION
        "Device reset reason code."
    ::= { strataonSystem 5 }

strataonCpuFrequency OBJECT-TYPE
    SYNTAX Gauge32
    UNITS "MHz"
    MAX-ACCESS read-only
    STATUS current
    DESCRIPTION
        "CPU frequency in MHz."
    ::= { strataonSystem 6 }

strataonModel OBJECT-TYPE
    SYNTAX DisplayString
    MAX-ACCESS read-only
    STATUS current
    DESCRIPTION
        "Device model string."
    ::= { strataonSystem 7 }

strataonSerialNumber OBJECT-TYPE
    SYNTAX DisplayString
    MAX-ACCESS read-only
    STATUS current
    DESCRIPTION
        "Device serial number."
    ::= { strataonSystem 8 }

strataonFirmwareVersion OBJECT-TYPE
    SYNTAX DisplayString
    MAX-ACCESS read-only
    STATUS current
    DESCRIPTION
        "Firmware version string."
    ::= { strataonSystem 9 }

strataonBuildDate OBJECT-TYPE
    SYNTAX DisplayString
    MAX-ACCESS read-only
    STATUS current
    DESCRIPTION
        "Firmware build date."
    ::= { strataonSystem 10 }

strataonSdkVersion OBJECT-TYPE
    SYNTAX DisplayString
    MAX-ACCESS read-only
    STATUS current
    DESCRIPTION
        "SDK or ESP-IDF version string."
    ::= { strataonSystem 11 }

strataonBuildTime OBJECT-TYPE
    SYNTAX DisplayString
    MAX-ACCESS read-only
    STATUS current
    DESCRIPTION
        "Firmware build time."
    ::= { strataonSystem 12 }

-- =============================================================
-- Common network group: 1.3.6.1.4.1.66204.2
-- =============================================================

strataonEthernetLink OBJECT-TYPE
    SYNTAX Integer32 (0..1)
    MAX-ACCESS read-only
    STATUS current
    DESCRIPTION
        "Ethernet link status. 0=down, 1=up."
    ::= { strataonNetwork 1 }

strataonEthernetIp OBJECT-TYPE
    SYNTAX DisplayString
    MAX-ACCESS read-only
    STATUS current
    DESCRIPTION
        "Ethernet IPv4 address."
    ::= { strataonNetwork 2 }

strataonEthernetMask OBJECT-TYPE
    SYNTAX DisplayString
    MAX-ACCESS read-only
    STATUS current
    DESCRIPTION
        "Ethernet IPv4 netmask."
    ::= { strataonNetwork 3 }

strataonEthernetGateway OBJECT-TYPE
    SYNTAX DisplayString
    MAX-ACCESS read-only
    STATUS current
    DESCRIPTION
        "Ethernet IPv4 gateway."
    ::= { strataonNetwork 4 }

strataonEthernetMac OBJECT-TYPE
    SYNTAX DisplayString
    MAX-ACCESS read-only
    STATUS current
    DESCRIPTION
        "Ethernet MAC address."
    ::= { strataonNetwork 5 }

strataonWifiLink OBJECT-TYPE
    SYNTAX Integer32 (0..1)
    MAX-ACCESS read-only
    STATUS current
    DESCRIPTION
        "Wi-Fi station link status. 0=down, 1=up."
    ::= { strataonNetwork 6 }

strataonWifiIp OBJECT-TYPE
    SYNTAX DisplayString
    MAX-ACCESS read-only
    STATUS current
    DESCRIPTION
        "Wi-Fi station IPv4 address."
    ::= { strataonNetwork 7 }

strataonWifiMask OBJECT-TYPE
    SYNTAX DisplayString
    MAX-ACCESS read-only
    STATUS current
    DESCRIPTION
        "Wi-Fi station IPv4 netmask."
    ::= { strataonNetwork 8 }

strataonWifiGateway OBJECT-TYPE
    SYNTAX DisplayString
    MAX-ACCESS read-only
    STATUS current
    DESCRIPTION
        "Wi-Fi station IPv4 gateway."
    ::= { strataonNetwork 9 }

strataonWifiMac OBJECT-TYPE
    SYNTAX DisplayString
    MAX-ACCESS read-only
    STATUS current
    DESCRIPTION
        "Wi-Fi station MAC address."
    ::= { strataonNetwork 10 }

strataonHostname OBJECT-TYPE
    SYNTAX DisplayString
    MAX-ACCESS read-only
    STATUS current
    DESCRIPTION
        "Device hostname."
    ::= { strataonNetwork 11 }

-- =============================================================
-- Products: 1.3.6.1.4.1.66204.10
-- =============================================================

strataonMiniPLC OBJECT-IDENTITY
    STATUS current
    DESCRIPTION "miniPLC product branch. Product ID = 1."
    ::= { strataonProducts 1 }

strataonSmartPDU OBJECT-IDENTITY
    STATUS current
    DESCRIPTION "smartPDU product branch. Product ID = 2."
    ::= { strataonProducts 2 }

strataonMiniENV OBJECT-IDENTITY
    STATUS current
    DESCRIPTION "miniENV product branch. Product ID = 3."
    ::= { strataonProducts 3 }

strataonSentiaMAN OBJECT-IDENTITY
    STATUS current
    DESCRIPTION "sentiaMAN product branch. Product ID = 4."
    ::= { strataonProducts 4 }

strataonSentiaPRO OBJECT-IDENTITY
    STATUS current
    DESCRIPTION "sentiaPRO product branch. Product ID = 5."
    ::= { strataonProducts 5 }

strataonSentiaLOK OBJECT-IDENTITY
    STATUS current
    DESCRIPTION "sentiaLOK product branch. Product ID = 6."
    ::= { strataonProducts 6 }

-- =============================================================
-- miniPLC branches: 1.3.6.1.4.1.66204.10.1
-- =============================================================

miniPLCDigitalInputs OBJECT-IDENTITY
    STATUS current
    DESCRIPTION "miniPLC digital inputs. Count is subidentifier 1; DI01 starts at subidentifier 101."
    ::= { strataonMiniPLC 1 }

miniPLCDigitalOutputs OBJECT-IDENTITY
    STATUS current
    DESCRIPTION "miniPLC digital outputs. Count is subidentifier 1; DO01 starts at subidentifier 101."
    ::= { strataonMiniPLC 2 }

miniPLCBooleanVariables OBJECT-IDENTITY
    STATUS current
    DESCRIPTION "miniPLC boolean variables. Count is subidentifier 1; BOOL01 starts at subidentifier 101."
    ::= { strataonMiniPLC 3 }

miniPLCLongVariables OBJECT-IDENTITY
    STATUS current
    DESCRIPTION "miniPLC signed 32-bit long integer variables. Count is subidentifier 1; LONG01 starts at subidentifier 101."
    ::= { strataonMiniPLC 4 }

miniPLCDigitalInputCount OBJECT-TYPE
    SYNTAX Integer32 (0..2147483647)
    MAX-ACCESS read-only
    STATUS current
    DESCRIPTION
        "Number of miniPLC digital inputs currently implemented."
    ::= { miniPLCDigitalInputs 1 }

miniPLCDigitalOutputCount OBJECT-TYPE
    SYNTAX Integer32 (0..2147483647)
    MAX-ACCESS read-only
    STATUS current
    DESCRIPTION
        "Number of miniPLC digital outputs currently implemented."
    ::= { miniPLCDigitalOutputs 1 }

miniPLCBooleanVariableCount OBJECT-TYPE
    SYNTAX Integer32 (0..2147483647)
    MAX-ACCESS read-only
    STATUS current
    DESCRIPTION
        "Number of miniPLC boolean variables currently implemented."
    ::= { miniPLCBooleanVariables 1 }

miniPLCLongVariableCount OBJECT-TYPE
    SYNTAX Integer32 (0..2147483647)
    MAX-ACCESS read-only
    STATUS current
    DESCRIPTION
        "Number of miniPLC long integer variables currently implemented."
    ::= { miniPLCLongVariables 1 }

-- miniPLC digital inputs 01..32 (subidentifiers 2..33)

miniPLCDI01 OBJECT-TYPE
    SYNTAX StrataonBinaryState
    MAX-ACCESS read-only
    STATUS current
    DESCRIPTION
        "miniPLC digital input 01."
    ::= { miniPLCDigitalInputs 101 }

miniPLCDI02 OBJECT-TYPE
    SYNTAX StrataonBinaryState
    MAX-ACCESS read-only
    STATUS current
    DESCRIPTION
        "miniPLC digital input 02."
    ::= { miniPLCDigitalInputs 102 }

miniPLCDI03 OBJECT-TYPE
    SYNTAX StrataonBinaryState
    MAX-ACCESS read-only
    STATUS current
    DESCRIPTION
        "miniPLC digital input 03."
    ::= { miniPLCDigitalInputs 103 }

miniPLCDI04 OBJECT-TYPE
    SYNTAX StrataonBinaryState
    MAX-ACCESS read-only
    STATUS current
    DESCRIPTION
        "miniPLC digital input 04."
    ::= { miniPLCDigitalInputs 104 }

miniPLCDI05 OBJECT-TYPE
    SYNTAX StrataonBinaryState
    MAX-ACCESS read-only
    STATUS current
    DESCRIPTION
        "miniPLC digital input 05."
    ::= { miniPLCDigitalInputs 105 }

miniPLCDI06 OBJECT-TYPE
    SYNTAX StrataonBinaryState
    MAX-ACCESS read-only
    STATUS current
    DESCRIPTION
        "miniPLC digital input 06."
    ::= { miniPLCDigitalInputs 106 }

miniPLCDI07 OBJECT-TYPE
    SYNTAX StrataonBinaryState
    MAX-ACCESS read-only
    STATUS current
    DESCRIPTION
        "miniPLC digital input 07."
    ::= { miniPLCDigitalInputs 107 }

miniPLCDI08 OBJECT-TYPE
    SYNTAX StrataonBinaryState
    MAX-ACCESS read-only
    STATUS current
    DESCRIPTION
        "miniPLC digital input 08."
    ::= { miniPLCDigitalInputs 108 }

miniPLCDI09 OBJECT-TYPE
    SYNTAX StrataonBinaryState
    MAX-ACCESS read-only
    STATUS current
    DESCRIPTION
        "miniPLC digital input 09."
    ::= { miniPLCDigitalInputs 109 }

miniPLCDI10 OBJECT-TYPE
    SYNTAX StrataonBinaryState
    MAX-ACCESS read-only
    STATUS current
    DESCRIPTION
        "miniPLC digital input 10."
    ::= { miniPLCDigitalInputs 110 }

miniPLCDI11 OBJECT-TYPE
    SYNTAX StrataonBinaryState
    MAX-ACCESS read-only
    STATUS current
    DESCRIPTION
        "miniPLC digital input 11."
    ::= { miniPLCDigitalInputs 111 }

miniPLCDI12 OBJECT-TYPE
    SYNTAX StrataonBinaryState
    MAX-ACCESS read-only
    STATUS current
    DESCRIPTION
        "miniPLC digital input 12."
    ::= { miniPLCDigitalInputs 112 }

miniPLCDI13 OBJECT-TYPE
    SYNTAX StrataonBinaryState
    MAX-ACCESS read-only
    STATUS current
    DESCRIPTION
        "miniPLC digital input 13."
    ::= { miniPLCDigitalInputs 113 }

miniPLCDI14 OBJECT-TYPE
    SYNTAX StrataonBinaryState
    MAX-ACCESS read-only
    STATUS current
    DESCRIPTION
        "miniPLC digital input 14."
    ::= { miniPLCDigitalInputs 114 }

miniPLCDI15 OBJECT-TYPE
    SYNTAX StrataonBinaryState
    MAX-ACCESS read-only
    STATUS current
    DESCRIPTION
        "miniPLC digital input 15."
    ::= { miniPLCDigitalInputs 115 }

miniPLCDI16 OBJECT-TYPE
    SYNTAX StrataonBinaryState
    MAX-ACCESS read-only
    STATUS current
    DESCRIPTION
        "miniPLC digital input 16."
    ::= { miniPLCDigitalInputs 116 }

miniPLCDI17 OBJECT-TYPE
    SYNTAX StrataonBinaryState
    MAX-ACCESS read-only
    STATUS current
    DESCRIPTION
        "miniPLC digital input 17."
    ::= { miniPLCDigitalInputs 117 }

miniPLCDI18 OBJECT-TYPE
    SYNTAX StrataonBinaryState
    MAX-ACCESS read-only
    STATUS current
    DESCRIPTION
        "miniPLC digital input 18."
    ::= { miniPLCDigitalInputs 118 }

miniPLCDI19 OBJECT-TYPE
    SYNTAX StrataonBinaryState
    MAX-ACCESS read-only
    STATUS current
    DESCRIPTION
        "miniPLC digital input 19."
    ::= { miniPLCDigitalInputs 119 }

miniPLCDI20 OBJECT-TYPE
    SYNTAX StrataonBinaryState
    MAX-ACCESS read-only
    STATUS current
    DESCRIPTION
        "miniPLC digital input 20."
    ::= { miniPLCDigitalInputs 120 }

miniPLCDI21 OBJECT-TYPE
    SYNTAX StrataonBinaryState
    MAX-ACCESS read-only
    STATUS current
    DESCRIPTION
        "miniPLC digital input 21."
    ::= { miniPLCDigitalInputs 121 }

miniPLCDI22 OBJECT-TYPE
    SYNTAX StrataonBinaryState
    MAX-ACCESS read-only
    STATUS current
    DESCRIPTION
        "miniPLC digital input 22."
    ::= { miniPLCDigitalInputs 122 }

miniPLCDI23 OBJECT-TYPE
    SYNTAX StrataonBinaryState
    MAX-ACCESS read-only
    STATUS current
    DESCRIPTION
        "miniPLC digital input 23."
    ::= { miniPLCDigitalInputs 123 }

miniPLCDI24 OBJECT-TYPE
    SYNTAX StrataonBinaryState
    MAX-ACCESS read-only
    STATUS current
    DESCRIPTION
        "miniPLC digital input 24."
    ::= { miniPLCDigitalInputs 124 }

miniPLCDI25 OBJECT-TYPE
    SYNTAX StrataonBinaryState
    MAX-ACCESS read-only
    STATUS current
    DESCRIPTION
        "miniPLC digital input 25."
    ::= { miniPLCDigitalInputs 125 }

miniPLCDI26 OBJECT-TYPE
    SYNTAX StrataonBinaryState
    MAX-ACCESS read-only
    STATUS current
    DESCRIPTION
        "miniPLC digital input 26."
    ::= { miniPLCDigitalInputs 126 }

miniPLCDI27 OBJECT-TYPE
    SYNTAX StrataonBinaryState
    MAX-ACCESS read-only
    STATUS current
    DESCRIPTION
        "miniPLC digital input 27."
    ::= { miniPLCDigitalInputs 127 }

miniPLCDI28 OBJECT-TYPE
    SYNTAX StrataonBinaryState
    MAX-ACCESS read-only
    STATUS current
    DESCRIPTION
        "miniPLC digital input 28."
    ::= { miniPLCDigitalInputs 128 }

miniPLCDI29 OBJECT-TYPE
    SYNTAX StrataonBinaryState
    MAX-ACCESS read-only
    STATUS current
    DESCRIPTION
        "miniPLC digital input 29."
    ::= { miniPLCDigitalInputs 129 }

miniPLCDI30 OBJECT-TYPE
    SYNTAX StrataonBinaryState
    MAX-ACCESS read-only
    STATUS current
    DESCRIPTION
        "miniPLC digital input 30."
    ::= { miniPLCDigitalInputs 130 }

miniPLCDI31 OBJECT-TYPE
    SYNTAX StrataonBinaryState
    MAX-ACCESS read-only
    STATUS current
    DESCRIPTION
        "miniPLC digital input 31."
    ::= { miniPLCDigitalInputs 131 }

miniPLCDI32 OBJECT-TYPE
    SYNTAX StrataonBinaryState
    MAX-ACCESS read-only
    STATUS current
    DESCRIPTION
        "miniPLC digital input 32."
    ::= { miniPLCDigitalInputs 132 }

-- miniPLC digital outputs 01..32 (subidentifiers 2..33)

miniPLCDO01 OBJECT-TYPE
    SYNTAX StrataonBinaryState
    MAX-ACCESS read-only
    STATUS current
    DESCRIPTION
        "miniPLC digital output 01."
    ::= { miniPLCDigitalOutputs 101 }

miniPLCDO02 OBJECT-TYPE
    SYNTAX StrataonBinaryState
    MAX-ACCESS read-only
    STATUS current
    DESCRIPTION
        "miniPLC digital output 02."
    ::= { miniPLCDigitalOutputs 102 }

miniPLCDO03 OBJECT-TYPE
    SYNTAX StrataonBinaryState
    MAX-ACCESS read-only
    STATUS current
    DESCRIPTION
        "miniPLC digital output 03."
    ::= { miniPLCDigitalOutputs 103 }

miniPLCDO04 OBJECT-TYPE
    SYNTAX StrataonBinaryState
    MAX-ACCESS read-only
    STATUS current
    DESCRIPTION
        "miniPLC digital output 04."
    ::= { miniPLCDigitalOutputs 104 }

miniPLCDO05 OBJECT-TYPE
    SYNTAX StrataonBinaryState
    MAX-ACCESS read-only
    STATUS current
    DESCRIPTION
        "miniPLC digital output 05."
    ::= { miniPLCDigitalOutputs 105 }

miniPLCDO06 OBJECT-TYPE
    SYNTAX StrataonBinaryState
    MAX-ACCESS read-only
    STATUS current
    DESCRIPTION
        "miniPLC digital output 06."
    ::= { miniPLCDigitalOutputs 106 }

miniPLCDO07 OBJECT-TYPE
    SYNTAX StrataonBinaryState
    MAX-ACCESS read-only
    STATUS current
    DESCRIPTION
        "miniPLC digital output 07."
    ::= { miniPLCDigitalOutputs 107 }

miniPLCDO08 OBJECT-TYPE
    SYNTAX StrataonBinaryState
    MAX-ACCESS read-only
    STATUS current
    DESCRIPTION
        "miniPLC digital output 08."
    ::= { miniPLCDigitalOutputs 108 }

miniPLCDO09 OBJECT-TYPE
    SYNTAX StrataonBinaryState
    MAX-ACCESS read-only
    STATUS current
    DESCRIPTION
        "miniPLC digital output 09."
    ::= { miniPLCDigitalOutputs 109 }

miniPLCDO10 OBJECT-TYPE
    SYNTAX StrataonBinaryState
    MAX-ACCESS read-only
    STATUS current
    DESCRIPTION
        "miniPLC digital output 10."
    ::= { miniPLCDigitalOutputs 110 }

miniPLCDO11 OBJECT-TYPE
    SYNTAX StrataonBinaryState
    MAX-ACCESS read-only
    STATUS current
    DESCRIPTION
        "miniPLC digital output 11."
    ::= { miniPLCDigitalOutputs 111 }

miniPLCDO12 OBJECT-TYPE
    SYNTAX StrataonBinaryState
    MAX-ACCESS read-only
    STATUS current
    DESCRIPTION
        "miniPLC digital output 12."
    ::= { miniPLCDigitalOutputs 112 }

miniPLCDO13 OBJECT-TYPE
    SYNTAX StrataonBinaryState
    MAX-ACCESS read-only
    STATUS current
    DESCRIPTION
        "miniPLC digital output 13."
    ::= { miniPLCDigitalOutputs 113 }

miniPLCDO14 OBJECT-TYPE
    SYNTAX StrataonBinaryState
    MAX-ACCESS read-only
    STATUS current
    DESCRIPTION
        "miniPLC digital output 14."
    ::= { miniPLCDigitalOutputs 114 }

miniPLCDO15 OBJECT-TYPE
    SYNTAX StrataonBinaryState
    MAX-ACCESS read-only
    STATUS current
    DESCRIPTION
        "miniPLC digital output 15."
    ::= { miniPLCDigitalOutputs 115 }

miniPLCDO16 OBJECT-TYPE
    SYNTAX StrataonBinaryState
    MAX-ACCESS read-only
    STATUS current
    DESCRIPTION
        "miniPLC digital output 16."
    ::= { miniPLCDigitalOutputs 116 }

miniPLCDO17 OBJECT-TYPE
    SYNTAX StrataonBinaryState
    MAX-ACCESS read-only
    STATUS current
    DESCRIPTION
        "miniPLC digital output 17."
    ::= { miniPLCDigitalOutputs 117 }

miniPLCDO18 OBJECT-TYPE
    SYNTAX StrataonBinaryState
    MAX-ACCESS read-only
    STATUS current
    DESCRIPTION
        "miniPLC digital output 18."
    ::= { miniPLCDigitalOutputs 118 }

miniPLCDO19 OBJECT-TYPE
    SYNTAX StrataonBinaryState
    MAX-ACCESS read-only
    STATUS current
    DESCRIPTION
        "miniPLC digital output 19."
    ::= { miniPLCDigitalOutputs 119 }

miniPLCDO20 OBJECT-TYPE
    SYNTAX StrataonBinaryState
    MAX-ACCESS read-only
    STATUS current
    DESCRIPTION
        "miniPLC digital output 20."
    ::= { miniPLCDigitalOutputs 120 }

miniPLCDO21 OBJECT-TYPE
    SYNTAX StrataonBinaryState
    MAX-ACCESS read-only
    STATUS current
    DESCRIPTION
        "miniPLC digital output 21."
    ::= { miniPLCDigitalOutputs 121 }

miniPLCDO22 OBJECT-TYPE
    SYNTAX StrataonBinaryState
    MAX-ACCESS read-only
    STATUS current
    DESCRIPTION
        "miniPLC digital output 22."
    ::= { miniPLCDigitalOutputs 122 }

miniPLCDO23 OBJECT-TYPE
    SYNTAX StrataonBinaryState
    MAX-ACCESS read-only
    STATUS current
    DESCRIPTION
        "miniPLC digital output 23."
    ::= { miniPLCDigitalOutputs 123 }

miniPLCDO24 OBJECT-TYPE
    SYNTAX StrataonBinaryState
    MAX-ACCESS read-only
    STATUS current
    DESCRIPTION
        "miniPLC digital output 24."
    ::= { miniPLCDigitalOutputs 124 }

miniPLCDO25 OBJECT-TYPE
    SYNTAX StrataonBinaryState
    MAX-ACCESS read-only
    STATUS current
    DESCRIPTION
        "miniPLC digital output 25."
    ::= { miniPLCDigitalOutputs 125 }

miniPLCDO26 OBJECT-TYPE
    SYNTAX StrataonBinaryState
    MAX-ACCESS read-only
    STATUS current
    DESCRIPTION
        "miniPLC digital output 26."
    ::= { miniPLCDigitalOutputs 126 }

miniPLCDO27 OBJECT-TYPE
    SYNTAX StrataonBinaryState
    MAX-ACCESS read-only
    STATUS current
    DESCRIPTION
        "miniPLC digital output 27."
    ::= { miniPLCDigitalOutputs 127 }

miniPLCDO28 OBJECT-TYPE
    SYNTAX StrataonBinaryState
    MAX-ACCESS read-only
    STATUS current
    DESCRIPTION
        "miniPLC digital output 28."
    ::= { miniPLCDigitalOutputs 128 }

miniPLCDO29 OBJECT-TYPE
    SYNTAX StrataonBinaryState
    MAX-ACCESS read-only
    STATUS current
    DESCRIPTION
        "miniPLC digital output 29."
    ::= { miniPLCDigitalOutputs 129 }

miniPLCDO30 OBJECT-TYPE
    SYNTAX StrataonBinaryState
    MAX-ACCESS read-only
    STATUS current
    DESCRIPTION
        "miniPLC digital output 30."
    ::= { miniPLCDigitalOutputs 130 }

miniPLCDO31 OBJECT-TYPE
    SYNTAX StrataonBinaryState
    MAX-ACCESS read-only
    STATUS current
    DESCRIPTION
        "miniPLC digital output 31."
    ::= { miniPLCDigitalOutputs 131 }

miniPLCDO32 OBJECT-TYPE
    SYNTAX StrataonBinaryState
    MAX-ACCESS read-only
    STATUS current
    DESCRIPTION
        "miniPLC digital output 32."
    ::= { miniPLCDigitalOutputs 132 }

-- miniPLC boolean variables 01..32 (subidentifiers 2..33)

miniPLCBOOL01 OBJECT-TYPE
    SYNTAX StrataonBinaryState
    MAX-ACCESS read-only
    STATUS current
    DESCRIPTION
        "miniPLC boolean variable 01."
    ::= { miniPLCBooleanVariables 101 }

miniPLCBOOL02 OBJECT-TYPE
    SYNTAX StrataonBinaryState
    MAX-ACCESS read-only
    STATUS current
    DESCRIPTION
        "miniPLC boolean variable 02."
    ::= { miniPLCBooleanVariables 102 }

miniPLCBOOL03 OBJECT-TYPE
    SYNTAX StrataonBinaryState
    MAX-ACCESS read-only
    STATUS current
    DESCRIPTION
        "miniPLC boolean variable 03."
    ::= { miniPLCBooleanVariables 103 }

miniPLCBOOL04 OBJECT-TYPE
    SYNTAX StrataonBinaryState
    MAX-ACCESS read-only
    STATUS current
    DESCRIPTION
        "miniPLC boolean variable 04."
    ::= { miniPLCBooleanVariables 104 }

miniPLCBOOL05 OBJECT-TYPE
    SYNTAX StrataonBinaryState
    MAX-ACCESS read-only
    STATUS current
    DESCRIPTION
        "miniPLC boolean variable 05."
    ::= { miniPLCBooleanVariables 105 }

miniPLCBOOL06 OBJECT-TYPE
    SYNTAX StrataonBinaryState
    MAX-ACCESS read-only
    STATUS current
    DESCRIPTION
        "miniPLC boolean variable 06."
    ::= { miniPLCBooleanVariables 106 }

miniPLCBOOL07 OBJECT-TYPE
    SYNTAX StrataonBinaryState
    MAX-ACCESS read-only
    STATUS current
    DESCRIPTION
        "miniPLC boolean variable 07."
    ::= { miniPLCBooleanVariables 107 }

miniPLCBOOL08 OBJECT-TYPE
    SYNTAX StrataonBinaryState
    MAX-ACCESS read-only
    STATUS current
    DESCRIPTION
        "miniPLC boolean variable 08."
    ::= { miniPLCBooleanVariables 108 }

miniPLCBOOL09 OBJECT-TYPE
    SYNTAX StrataonBinaryState
    MAX-ACCESS read-only
    STATUS current
    DESCRIPTION
        "miniPLC boolean variable 09."
    ::= { miniPLCBooleanVariables 109 }

miniPLCBOOL10 OBJECT-TYPE
    SYNTAX StrataonBinaryState
    MAX-ACCESS read-only
    STATUS current
    DESCRIPTION
        "miniPLC boolean variable 10."
    ::= { miniPLCBooleanVariables 110 }

miniPLCBOOL11 OBJECT-TYPE
    SYNTAX StrataonBinaryState
    MAX-ACCESS read-only
    STATUS current
    DESCRIPTION
        "miniPLC boolean variable 11."
    ::= { miniPLCBooleanVariables 111 }

miniPLCBOOL12 OBJECT-TYPE
    SYNTAX StrataonBinaryState
    MAX-ACCESS read-only
    STATUS current
    DESCRIPTION
        "miniPLC boolean variable 12."
    ::= { miniPLCBooleanVariables 112 }

miniPLCBOOL13 OBJECT-TYPE
    SYNTAX StrataonBinaryState
    MAX-ACCESS read-only
    STATUS current
    DESCRIPTION
        "miniPLC boolean variable 13."
    ::= { miniPLCBooleanVariables 113 }

miniPLCBOOL14 OBJECT-TYPE
    SYNTAX StrataonBinaryState
    MAX-ACCESS read-only
    STATUS current
    DESCRIPTION
        "miniPLC boolean variable 14."
    ::= { miniPLCBooleanVariables 114 }

miniPLCBOOL15 OBJECT-TYPE
    SYNTAX StrataonBinaryState
    MAX-ACCESS read-only
    STATUS current
    DESCRIPTION
        "miniPLC boolean variable 15."
    ::= { miniPLCBooleanVariables 115 }

miniPLCBOOL16 OBJECT-TYPE
    SYNTAX StrataonBinaryState
    MAX-ACCESS read-only
    STATUS current
    DESCRIPTION
        "miniPLC boolean variable 16."
    ::= { miniPLCBooleanVariables 116 }

miniPLCBOOL17 OBJECT-TYPE
    SYNTAX StrataonBinaryState
    MAX-ACCESS read-only
    STATUS current
    DESCRIPTION
        "miniPLC boolean variable 17."
    ::= { miniPLCBooleanVariables 117 }

miniPLCBOOL18 OBJECT-TYPE
    SYNTAX StrataonBinaryState
    MAX-ACCESS read-only
    STATUS current
    DESCRIPTION
        "miniPLC boolean variable 18."
    ::= { miniPLCBooleanVariables 118 }

miniPLCBOOL19 OBJECT-TYPE
    SYNTAX StrataonBinaryState
    MAX-ACCESS read-only
    STATUS current
    DESCRIPTION
        "miniPLC boolean variable 19."
    ::= { miniPLCBooleanVariables 119 }

miniPLCBOOL20 OBJECT-TYPE
    SYNTAX StrataonBinaryState
    MAX-ACCESS read-only
    STATUS current
    DESCRIPTION
        "miniPLC boolean variable 20."
    ::= { miniPLCBooleanVariables 120 }

miniPLCBOOL21 OBJECT-TYPE
    SYNTAX StrataonBinaryState
    MAX-ACCESS read-only
    STATUS current
    DESCRIPTION
        "miniPLC boolean variable 21."
    ::= { miniPLCBooleanVariables 121 }

miniPLCBOOL22 OBJECT-TYPE
    SYNTAX StrataonBinaryState
    MAX-ACCESS read-only
    STATUS current
    DESCRIPTION
        "miniPLC boolean variable 22."
    ::= { miniPLCBooleanVariables 122 }

miniPLCBOOL23 OBJECT-TYPE
    SYNTAX StrataonBinaryState
    MAX-ACCESS read-only
    STATUS current
    DESCRIPTION
        "miniPLC boolean variable 23."
    ::= { miniPLCBooleanVariables 123 }

miniPLCBOOL24 OBJECT-TYPE
    SYNTAX StrataonBinaryState
    MAX-ACCESS read-only
    STATUS current
    DESCRIPTION
        "miniPLC boolean variable 24."
    ::= { miniPLCBooleanVariables 124 }

miniPLCBOOL25 OBJECT-TYPE
    SYNTAX StrataonBinaryState
    MAX-ACCESS read-only
    STATUS current
    DESCRIPTION
        "miniPLC boolean variable 25."
    ::= { miniPLCBooleanVariables 125 }

miniPLCBOOL26 OBJECT-TYPE
    SYNTAX StrataonBinaryState
    MAX-ACCESS read-only
    STATUS current
    DESCRIPTION
        "miniPLC boolean variable 26."
    ::= { miniPLCBooleanVariables 126 }

miniPLCBOOL27 OBJECT-TYPE
    SYNTAX StrataonBinaryState
    MAX-ACCESS read-only
    STATUS current
    DESCRIPTION
        "miniPLC boolean variable 27."
    ::= { miniPLCBooleanVariables 127 }

miniPLCBOOL28 OBJECT-TYPE
    SYNTAX StrataonBinaryState
    MAX-ACCESS read-only
    STATUS current
    DESCRIPTION
        "miniPLC boolean variable 28."
    ::= { miniPLCBooleanVariables 128 }

miniPLCBOOL29 OBJECT-TYPE
    SYNTAX StrataonBinaryState
    MAX-ACCESS read-only
    STATUS current
    DESCRIPTION
        "miniPLC boolean variable 29."
    ::= { miniPLCBooleanVariables 129 }

miniPLCBOOL30 OBJECT-TYPE
    SYNTAX StrataonBinaryState
    MAX-ACCESS read-only
    STATUS current
    DESCRIPTION
        "miniPLC boolean variable 30."
    ::= { miniPLCBooleanVariables 130 }

miniPLCBOOL31 OBJECT-TYPE
    SYNTAX StrataonBinaryState
    MAX-ACCESS read-only
    STATUS current
    DESCRIPTION
        "miniPLC boolean variable 31."
    ::= { miniPLCBooleanVariables 131 }

miniPLCBOOL32 OBJECT-TYPE
    SYNTAX StrataonBinaryState
    MAX-ACCESS read-only
    STATUS current
    DESCRIPTION
        "miniPLC boolean variable 32."
    ::= { miniPLCBooleanVariables 132 }

-- miniPLC long integer variables 01..32 (subidentifiers 2..33)

miniPLCLONG01 OBJECT-TYPE
    SYNTAX Integer32
    MAX-ACCESS read-only
    STATUS current
    DESCRIPTION
        "miniPLC long integer variable 01."
    ::= { miniPLCLongVariables 101 }

miniPLCLONG02 OBJECT-TYPE
    SYNTAX Integer32
    MAX-ACCESS read-only
    STATUS current
    DESCRIPTION
        "miniPLC long integer variable 02."
    ::= { miniPLCLongVariables 102 }

miniPLCLONG03 OBJECT-TYPE
    SYNTAX Integer32
    MAX-ACCESS read-only
    STATUS current
    DESCRIPTION
        "miniPLC long integer variable 03."
    ::= { miniPLCLongVariables 103 }

miniPLCLONG04 OBJECT-TYPE
    SYNTAX Integer32
    MAX-ACCESS read-only
    STATUS current
    DESCRIPTION
        "miniPLC long integer variable 04."
    ::= { miniPLCLongVariables 104 }

miniPLCLONG05 OBJECT-TYPE
    SYNTAX Integer32
    MAX-ACCESS read-only
    STATUS current
    DESCRIPTION
        "miniPLC long integer variable 05."
    ::= { miniPLCLongVariables 105 }

miniPLCLONG06 OBJECT-TYPE
    SYNTAX Integer32
    MAX-ACCESS read-only
    STATUS current
    DESCRIPTION
        "miniPLC long integer variable 06."
    ::= { miniPLCLongVariables 106 }

miniPLCLONG07 OBJECT-TYPE
    SYNTAX Integer32
    MAX-ACCESS read-only
    STATUS current
    DESCRIPTION
        "miniPLC long integer variable 07."
    ::= { miniPLCLongVariables 107 }

miniPLCLONG08 OBJECT-TYPE
    SYNTAX Integer32
    MAX-ACCESS read-only
    STATUS current
    DESCRIPTION
        "miniPLC long integer variable 08."
    ::= { miniPLCLongVariables 108 }

miniPLCLONG09 OBJECT-TYPE
    SYNTAX Integer32
    MAX-ACCESS read-only
    STATUS current
    DESCRIPTION
        "miniPLC long integer variable 09."
    ::= { miniPLCLongVariables 109 }

miniPLCLONG10 OBJECT-TYPE
    SYNTAX Integer32
    MAX-ACCESS read-only
    STATUS current
    DESCRIPTION
        "miniPLC long integer variable 10."
    ::= { miniPLCLongVariables 110 }

miniPLCLONG11 OBJECT-TYPE
    SYNTAX Integer32
    MAX-ACCESS read-only
    STATUS current
    DESCRIPTION
        "miniPLC long integer variable 11."
    ::= { miniPLCLongVariables 111 }

miniPLCLONG12 OBJECT-TYPE
    SYNTAX Integer32
    MAX-ACCESS read-only
    STATUS current
    DESCRIPTION
        "miniPLC long integer variable 12."
    ::= { miniPLCLongVariables 112 }

miniPLCLONG13 OBJECT-TYPE
    SYNTAX Integer32
    MAX-ACCESS read-only
    STATUS current
    DESCRIPTION
        "miniPLC long integer variable 13."
    ::= { miniPLCLongVariables 113 }

miniPLCLONG14 OBJECT-TYPE
    SYNTAX Integer32
    MAX-ACCESS read-only
    STATUS current
    DESCRIPTION
        "miniPLC long integer variable 14."
    ::= { miniPLCLongVariables 114 }

miniPLCLONG15 OBJECT-TYPE
    SYNTAX Integer32
    MAX-ACCESS read-only
    STATUS current
    DESCRIPTION
        "miniPLC long integer variable 15."
    ::= { miniPLCLongVariables 115 }

miniPLCLONG16 OBJECT-TYPE
    SYNTAX Integer32
    MAX-ACCESS read-only
    STATUS current
    DESCRIPTION
        "miniPLC long integer variable 16."
    ::= { miniPLCLongVariables 116 }

miniPLCLONG17 OBJECT-TYPE
    SYNTAX Integer32
    MAX-ACCESS read-only
    STATUS current
    DESCRIPTION
        "miniPLC long integer variable 17."
    ::= { miniPLCLongVariables 117 }

miniPLCLONG18 OBJECT-TYPE
    SYNTAX Integer32
    MAX-ACCESS read-only
    STATUS current
    DESCRIPTION
        "miniPLC long integer variable 18."
    ::= { miniPLCLongVariables 118 }

miniPLCLONG19 OBJECT-TYPE
    SYNTAX Integer32
    MAX-ACCESS read-only
    STATUS current
    DESCRIPTION
        "miniPLC long integer variable 19."
    ::= { miniPLCLongVariables 119 }

miniPLCLONG20 OBJECT-TYPE
    SYNTAX Integer32
    MAX-ACCESS read-only
    STATUS current
    DESCRIPTION
        "miniPLC long integer variable 20."
    ::= { miniPLCLongVariables 120 }

miniPLCLONG21 OBJECT-TYPE
    SYNTAX Integer32
    MAX-ACCESS read-only
    STATUS current
    DESCRIPTION
        "miniPLC long integer variable 21."
    ::= { miniPLCLongVariables 121 }

miniPLCLONG22 OBJECT-TYPE
    SYNTAX Integer32
    MAX-ACCESS read-only
    STATUS current
    DESCRIPTION
        "miniPLC long integer variable 22."
    ::= { miniPLCLongVariables 122 }

miniPLCLONG23 OBJECT-TYPE
    SYNTAX Integer32
    MAX-ACCESS read-only
    STATUS current
    DESCRIPTION
        "miniPLC long integer variable 23."
    ::= { miniPLCLongVariables 123 }

miniPLCLONG24 OBJECT-TYPE
    SYNTAX Integer32
    MAX-ACCESS read-only
    STATUS current
    DESCRIPTION
        "miniPLC long integer variable 24."
    ::= { miniPLCLongVariables 124 }

miniPLCLONG25 OBJECT-TYPE
    SYNTAX Integer32
    MAX-ACCESS read-only
    STATUS current
    DESCRIPTION
        "miniPLC long integer variable 25."
    ::= { miniPLCLongVariables 125 }

miniPLCLONG26 OBJECT-TYPE
    SYNTAX Integer32
    MAX-ACCESS read-only
    STATUS current
    DESCRIPTION
        "miniPLC long integer variable 26."
    ::= { miniPLCLongVariables 126 }

miniPLCLONG27 OBJECT-TYPE
    SYNTAX Integer32
    MAX-ACCESS read-only
    STATUS current
    DESCRIPTION
        "miniPLC long integer variable 27."
    ::= { miniPLCLongVariables 127 }

miniPLCLONG28 OBJECT-TYPE
    SYNTAX Integer32
    MAX-ACCESS read-only
    STATUS current
    DESCRIPTION
        "miniPLC long integer variable 28."
    ::= { miniPLCLongVariables 128 }

miniPLCLONG29 OBJECT-TYPE
    SYNTAX Integer32
    MAX-ACCESS read-only
    STATUS current
    DESCRIPTION
        "miniPLC long integer variable 29."
    ::= { miniPLCLongVariables 129 }

miniPLCLONG30 OBJECT-TYPE
    SYNTAX Integer32
    MAX-ACCESS read-only
    STATUS current
    DESCRIPTION
        "miniPLC long integer variable 30."
    ::= { miniPLCLongVariables 130 }

miniPLCLONG31 OBJECT-TYPE
    SYNTAX Integer32
    MAX-ACCESS read-only
    STATUS current
    DESCRIPTION
        "miniPLC long integer variable 31."
    ::= { miniPLCLongVariables 131 }

miniPLCLONG32 OBJECT-TYPE
    SYNTAX Integer32
    MAX-ACCESS read-only
    STATUS current
    DESCRIPTION
        "miniPLC long integer variable 32."
    ::= { miniPLCLongVariables 132 }

-- =============================================================
-- smartPDU branches: 1.3.6.1.4.1.66204.10.2
-- =============================================================

smartPDURelays OBJECT-IDENTITY
    STATUS current
    DESCRIPTION "smartPDU relay/outlet status group. Count is subidentifier 1; relay01 starts at subidentifier 101."
    ::= { strataonSmartPDU 1 }

smartPDURelayCount OBJECT-TYPE
    SYNTAX Integer32 (0..2147483647)
    MAX-ACCESS read-only
    STATUS current
    DESCRIPTION
        "Number of smartPDU relays/outlets currently implemented."
    ::= { smartPDURelays 1 }

smartPDURelay01 OBJECT-TYPE
    SYNTAX StrataonBinaryState
    MAX-ACCESS read-only
    STATUS current
    DESCRIPTION
        "smartPDU relay/outlet 01 status. 0=off, 1=on."
    ::= { smartPDURelays 101 }

smartPDURelay02 OBJECT-TYPE
    SYNTAX StrataonBinaryState
    MAX-ACCESS read-only
    STATUS current
    DESCRIPTION
        "smartPDU relay/outlet 02 status. 0=off, 1=on."
    ::= { smartPDURelays 102 }

smartPDURelay03 OBJECT-TYPE
    SYNTAX StrataonBinaryState
    MAX-ACCESS read-only
    STATUS current
    DESCRIPTION
        "smartPDU relay/outlet 03 status. 0=off, 1=on."
    ::= { smartPDURelays 103 }

smartPDURelay04 OBJECT-TYPE
    SYNTAX StrataonBinaryState
    MAX-ACCESS read-only
    STATUS current
    DESCRIPTION
        "smartPDU relay/outlet 04 status. 0=off, 1=on."
    ::= { smartPDURelays 104 }

smartPDURelay05 OBJECT-TYPE
    SYNTAX StrataonBinaryState
    MAX-ACCESS read-only
    STATUS current
    DESCRIPTION
        "smartPDU relay/outlet 05 status. 0=off, 1=on."
    ::= { smartPDURelays 105 }

smartPDURelay06 OBJECT-TYPE
    SYNTAX StrataonBinaryState
    MAX-ACCESS read-only
    STATUS current
    DESCRIPTION
        "smartPDU relay/outlet 06 status. 0=off, 1=on."
    ::= { smartPDURelays 106 }

smartPDURelay07 OBJECT-TYPE
    SYNTAX StrataonBinaryState
    MAX-ACCESS read-only
    STATUS current
    DESCRIPTION
        "smartPDU relay/outlet 07 status. 0=off, 1=on."
    ::= { smartPDURelays 107 }

smartPDURelay08 OBJECT-TYPE
    SYNTAX StrataonBinaryState
    MAX-ACCESS read-only
    STATUS current
    DESCRIPTION
        "smartPDU relay/outlet 08 status. 0=off, 1=on."
    ::= { smartPDURelays 108 }

smartPDURelayStatistics OBJECT-IDENTITY
    STATUS current
    DESCRIPTION
        "Persistent smartPDU relay operation statistics. Relay counters use subidentifiers 101 through 108."
    ::= { strataonSmartPDU 2 }

smartPDURelayOnCount01 OBJECT-TYPE
    SYNTAX Gauge32
    MAX-ACCESS read-only
    STATUS current
    DESCRIPTION
        "Number of commands that switched relay 01 on."
    ::= { smartPDURelayStatistics 101 }

smartPDURelayOnCount02 OBJECT-TYPE
    SYNTAX Gauge32
    MAX-ACCESS read-only
    STATUS current
    DESCRIPTION
        "Number of commands that switched relay 02 on."
    ::= { smartPDURelayStatistics 102 }

smartPDURelayOnCount03 OBJECT-TYPE
    SYNTAX Gauge32
    MAX-ACCESS read-only
    STATUS current
    DESCRIPTION
        "Number of commands that switched relay 03 on."
    ::= { smartPDURelayStatistics 103 }

smartPDURelayOnCount04 OBJECT-TYPE
    SYNTAX Gauge32
    MAX-ACCESS read-only
    STATUS current
    DESCRIPTION
        "Number of commands that switched relay 04 on."
    ::= { smartPDURelayStatistics 104 }

smartPDURelayOnCount05 OBJECT-TYPE
    SYNTAX Gauge32
    MAX-ACCESS read-only
    STATUS current
    DESCRIPTION
        "Number of commands that switched relay 05 on."
    ::= { smartPDURelayStatistics 105 }

smartPDURelayOnCount06 OBJECT-TYPE
    SYNTAX Gauge32
    MAX-ACCESS read-only
    STATUS current
    DESCRIPTION
        "Number of commands that switched relay 06 on."
    ::= { smartPDURelayStatistics 106 }

smartPDURelayOnCount07 OBJECT-TYPE
    SYNTAX Gauge32
    MAX-ACCESS read-only
    STATUS current
    DESCRIPTION
        "Number of commands that switched relay 07 on."
    ::= { smartPDURelayStatistics 107 }

smartPDURelayOnCount08 OBJECT-TYPE
    SYNTAX Gauge32
    MAX-ACCESS read-only
    STATUS current
    DESCRIPTION
        "Number of commands that switched relay 08 on."
    ::= { smartPDURelayStatistics 108 }

-- =============================================================
-- Reserved notification identities
-- =============================================================

strataonDeviceRestart OBJECT-IDENTITY
    STATUS current
    DESCRIPTION "Reserved notification identity for device restart."
    ::= { strataonNotifications 1 }

strataonEthernetDown OBJECT-IDENTITY
    STATUS current
    DESCRIPTION "Reserved notification identity for Ethernet down."
    ::= { strataonNotifications 2 }

strataonEthernetUp OBJECT-IDENTITY
    STATUS current
    DESCRIPTION "Reserved notification identity for Ethernet up."
    ::= { strataonNotifications 3 }

strataonWifiDown OBJECT-IDENTITY
    STATUS current
    DESCRIPTION "Reserved notification identity for Wi-Fi down."
    ::= { strataonNotifications 4 }

strataonWifiUp OBJECT-IDENTITY
    STATUS current
    DESCRIPTION "Reserved notification identity for Wi-Fi up."
    ::= { strataonNotifications 5 }

strataonRelayChanged OBJECT-IDENTITY
    STATUS current
    DESCRIPTION "Reserved notification identity for relay status changes."
    ::= { strataonNotifications 6 }

strataonInputChanged OBJECT-IDENTITY
    STATUS current
    DESCRIPTION "Reserved notification identity for digital input changes."
    ::= { strataonNotifications 7 }

strataonWatchdogTimeout OBJECT-IDENTITY
    STATUS current
    DESCRIPTION "Reserved notification identity for watchdog timeout."
    ::= { strataonNotifications 8 }

strataonAlarm OBJECT-IDENTITY
    STATUS current
    DESCRIPTION "Reserved notification identity for generic alarm."
    ::= { strataonNotifications 9 }

-- =============================================================
-- miniENV branches: 1.3.6.1.4.1.66204.10.3
-- =============================================================

miniENVDigitalInputs OBJECT-IDENTITY
    STATUS current
    DESCRIPTION "miniENV digital inputs. Count is subidentifier 1; DI01 starts at subidentifier 101."
    ::= { strataonMiniENV 1 }

miniENVDigitalOutputs OBJECT-IDENTITY
    STATUS current
    DESCRIPTION "miniENV digital outputs. Count is subidentifier 1; DO01 starts at subidentifier 101."
    ::= { strataonMiniENV 2 }

miniENVBooleanVariables OBJECT-IDENTITY
    STATUS current
    DESCRIPTION "miniENV boolean variables. Count is subidentifier 1; BOOL01 starts at subidentifier 101."
    ::= { strataonMiniENV 3 }

miniENVLongVariables OBJECT-IDENTITY
    STATUS current
    DESCRIPTION "miniENV signed 32-bit long integer variables. Count is subidentifier 1; LONG01 starts at subidentifier 101."
    ::= { strataonMiniENV 4 }

miniENVAnalogInputs OBJECT-IDENTITY
    STATUS current
    DESCRIPTION "miniENV environmental analog inputs. Count is subidentifier 1; values start at subidentifier 101."
    ::= { strataonMiniENV 5 }

miniENVDigitalInputCount OBJECT-TYPE
    SYNTAX Integer32 (9)
    MAX-ACCESS read-only
    STATUS current
    DESCRIPTION "Number of miniENV digital inputs implemented."
    ::= { miniENVDigitalInputs 1 }

miniENVDigitalOutputCount OBJECT-TYPE
    SYNTAX Integer32 (2)
    MAX-ACCESS read-only
    STATUS current
    DESCRIPTION "Number of miniENV digital outputs implemented."
    ::= { miniENVDigitalOutputs 1 }

miniENVBooleanVariableCount OBJECT-TYPE
    SYNTAX Integer32 (32)
    MAX-ACCESS read-only
    STATUS current
    DESCRIPTION "Number of miniENV boolean variables implemented."
    ::= { miniENVBooleanVariables 1 }

miniENVLongVariableCount OBJECT-TYPE
    SYNTAX Integer32 (32)
    MAX-ACCESS read-only
    STATUS current
    DESCRIPTION "Number of miniENV long integer variables implemented."
    ::= { miniENVLongVariables 1 }

miniENVAnalogInputCount OBJECT-TYPE
    SYNTAX Integer32 (8)
    MAX-ACCESS read-only
    STATUS current
    DESCRIPTION "Number of miniENV environmental analog inputs implemented."
    ::= { miniENVAnalogInputs 1 }

-- miniENV digital inputs 01..09 (subidentifiers 101..109)

miniENVDI01 OBJECT-TYPE
    SYNTAX StrataonBinaryState
    MAX-ACCESS read-only
    STATUS current
    DESCRIPTION "miniENV digital input 01."
    ::= { miniENVDigitalInputs 101 }

miniENVDI02 OBJECT-TYPE
    SYNTAX StrataonBinaryState
    MAX-ACCESS read-only
    STATUS current
    DESCRIPTION "miniENV digital input 02."
    ::= { miniENVDigitalInputs 102 }

miniENVDI03 OBJECT-TYPE
    SYNTAX StrataonBinaryState
    MAX-ACCESS read-only
    STATUS current
    DESCRIPTION "miniENV digital input 03."
    ::= { miniENVDigitalInputs 103 }

miniENVDI04 OBJECT-TYPE
    SYNTAX StrataonBinaryState
    MAX-ACCESS read-only
    STATUS current
    DESCRIPTION "miniENV digital input 04."
    ::= { miniENVDigitalInputs 104 }

miniENVDI05 OBJECT-TYPE
    SYNTAX StrataonBinaryState
    MAX-ACCESS read-only
    STATUS current
    DESCRIPTION "miniENV digital input 05."
    ::= { miniENVDigitalInputs 105 }

miniENVDI06 OBJECT-TYPE
    SYNTAX StrataonBinaryState
    MAX-ACCESS read-only
    STATUS current
    DESCRIPTION "miniENV digital input 06."
    ::= { miniENVDigitalInputs 106 }

miniENVDI07 OBJECT-TYPE
    SYNTAX StrataonBinaryState
    MAX-ACCESS read-only
    STATUS current
    DESCRIPTION "miniENV digital input 07."
    ::= { miniENVDigitalInputs 107 }

miniENVDI08 OBJECT-TYPE
    SYNTAX StrataonBinaryState
    MAX-ACCESS read-only
    STATUS current
    DESCRIPTION "miniENV digital input 08."
    ::= { miniENVDigitalInputs 108 }

miniENVDI09 OBJECT-TYPE
    SYNTAX StrataonBinaryState
    MAX-ACCESS read-only
    STATUS current
    DESCRIPTION "miniENV digital input 09."
    ::= { miniENVDigitalInputs 109 }

-- miniENV digital outputs 01..02 (subidentifiers 101..102)

miniENVDO01 OBJECT-TYPE
    SYNTAX StrataonBinaryState
    MAX-ACCESS read-only
    STATUS current
    DESCRIPTION "miniENV digital output 01."
    ::= { miniENVDigitalOutputs 101 }

miniENVDO02 OBJECT-TYPE
    SYNTAX StrataonBinaryState
    MAX-ACCESS read-only
    STATUS current
    DESCRIPTION "miniENV digital output 02."
    ::= { miniENVDigitalOutputs 102 }

-- miniENV boolean variables 01..32 (subidentifiers 101..132)

miniENVBOOL01 OBJECT-TYPE
    SYNTAX StrataonBinaryState
    MAX-ACCESS read-only
    STATUS current
    DESCRIPTION "miniENV boolean variable 01."
    ::= { miniENVBooleanVariables 101 }

miniENVBOOL02 OBJECT-TYPE
    SYNTAX StrataonBinaryState
    MAX-ACCESS read-only
    STATUS current
    DESCRIPTION "miniENV boolean variable 02."
    ::= { miniENVBooleanVariables 102 }

miniENVBOOL03 OBJECT-TYPE
    SYNTAX StrataonBinaryState
    MAX-ACCESS read-only
    STATUS current
    DESCRIPTION "miniENV boolean variable 03."
    ::= { miniENVBooleanVariables 103 }

miniENVBOOL04 OBJECT-TYPE
    SYNTAX StrataonBinaryState
    MAX-ACCESS read-only
    STATUS current
    DESCRIPTION "miniENV boolean variable 04."
    ::= { miniENVBooleanVariables 104 }

miniENVBOOL05 OBJECT-TYPE
    SYNTAX StrataonBinaryState
    MAX-ACCESS read-only
    STATUS current
    DESCRIPTION "miniENV boolean variable 05."
    ::= { miniENVBooleanVariables 105 }

miniENVBOOL06 OBJECT-TYPE
    SYNTAX StrataonBinaryState
    MAX-ACCESS read-only
    STATUS current
    DESCRIPTION "miniENV boolean variable 06."
    ::= { miniENVBooleanVariables 106 }

miniENVBOOL07 OBJECT-TYPE
    SYNTAX StrataonBinaryState
    MAX-ACCESS read-only
    STATUS current
    DESCRIPTION "miniENV boolean variable 07."
    ::= { miniENVBooleanVariables 107 }

miniENVBOOL08 OBJECT-TYPE
    SYNTAX StrataonBinaryState
    MAX-ACCESS read-only
    STATUS current
    DESCRIPTION "miniENV boolean variable 08."
    ::= { miniENVBooleanVariables 108 }

miniENVBOOL09 OBJECT-TYPE
    SYNTAX StrataonBinaryState
    MAX-ACCESS read-only
    STATUS current
    DESCRIPTION "miniENV boolean variable 09."
    ::= { miniENVBooleanVariables 109 }

miniENVBOOL10 OBJECT-TYPE
    SYNTAX StrataonBinaryState
    MAX-ACCESS read-only
    STATUS current
    DESCRIPTION "miniENV boolean variable 10."
    ::= { miniENVBooleanVariables 110 }

miniENVBOOL11 OBJECT-TYPE
    SYNTAX StrataonBinaryState
    MAX-ACCESS read-only
    STATUS current
    DESCRIPTION "miniENV boolean variable 11."
    ::= { miniENVBooleanVariables 111 }

miniENVBOOL12 OBJECT-TYPE
    SYNTAX StrataonBinaryState
    MAX-ACCESS read-only
    STATUS current
    DESCRIPTION "miniENV boolean variable 12."
    ::= { miniENVBooleanVariables 112 }

miniENVBOOL13 OBJECT-TYPE
    SYNTAX StrataonBinaryState
    MAX-ACCESS read-only
    STATUS current
    DESCRIPTION "miniENV boolean variable 13."
    ::= { miniENVBooleanVariables 113 }

miniENVBOOL14 OBJECT-TYPE
    SYNTAX StrataonBinaryState
    MAX-ACCESS read-only
    STATUS current
    DESCRIPTION "miniENV boolean variable 14."
    ::= { miniENVBooleanVariables 114 }

miniENVBOOL15 OBJECT-TYPE
    SYNTAX StrataonBinaryState
    MAX-ACCESS read-only
    STATUS current
    DESCRIPTION "miniENV boolean variable 15."
    ::= { miniENVBooleanVariables 115 }

miniENVBOOL16 OBJECT-TYPE
    SYNTAX StrataonBinaryState
    MAX-ACCESS read-only
    STATUS current
    DESCRIPTION "miniENV boolean variable 16."
    ::= { miniENVBooleanVariables 116 }

miniENVBOOL17 OBJECT-TYPE
    SYNTAX StrataonBinaryState
    MAX-ACCESS read-only
    STATUS current
    DESCRIPTION "miniENV boolean variable 17."
    ::= { miniENVBooleanVariables 117 }

miniENVBOOL18 OBJECT-TYPE
    SYNTAX StrataonBinaryState
    MAX-ACCESS read-only
    STATUS current
    DESCRIPTION "miniENV boolean variable 18."
    ::= { miniENVBooleanVariables 118 }

miniENVBOOL19 OBJECT-TYPE
    SYNTAX StrataonBinaryState
    MAX-ACCESS read-only
    STATUS current
    DESCRIPTION "miniENV boolean variable 19."
    ::= { miniENVBooleanVariables 119 }

miniENVBOOL20 OBJECT-TYPE
    SYNTAX StrataonBinaryState
    MAX-ACCESS read-only
    STATUS current
    DESCRIPTION "miniENV boolean variable 20."
    ::= { miniENVBooleanVariables 120 }

miniENVBOOL21 OBJECT-TYPE
    SYNTAX StrataonBinaryState
    MAX-ACCESS read-only
    STATUS current
    DESCRIPTION "miniENV boolean variable 21."
    ::= { miniENVBooleanVariables 121 }

miniENVBOOL22 OBJECT-TYPE
    SYNTAX StrataonBinaryState
    MAX-ACCESS read-only
    STATUS current
    DESCRIPTION "miniENV boolean variable 22."
    ::= { miniENVBooleanVariables 122 }

miniENVBOOL23 OBJECT-TYPE
    SYNTAX StrataonBinaryState
    MAX-ACCESS read-only
    STATUS current
    DESCRIPTION "miniENV boolean variable 23."
    ::= { miniENVBooleanVariables 123 }

miniENVBOOL24 OBJECT-TYPE
    SYNTAX StrataonBinaryState
    MAX-ACCESS read-only
    STATUS current
    DESCRIPTION "miniENV boolean variable 24."
    ::= { miniENVBooleanVariables 124 }

miniENVBOOL25 OBJECT-TYPE
    SYNTAX StrataonBinaryState
    MAX-ACCESS read-only
    STATUS current
    DESCRIPTION "miniENV boolean variable 25."
    ::= { miniENVBooleanVariables 125 }

miniENVBOOL26 OBJECT-TYPE
    SYNTAX StrataonBinaryState
    MAX-ACCESS read-only
    STATUS current
    DESCRIPTION "miniENV boolean variable 26."
    ::= { miniENVBooleanVariables 126 }

miniENVBOOL27 OBJECT-TYPE
    SYNTAX StrataonBinaryState
    MAX-ACCESS read-only
    STATUS current
    DESCRIPTION "miniENV boolean variable 27."
    ::= { miniENVBooleanVariables 127 }

miniENVBOOL28 OBJECT-TYPE
    SYNTAX StrataonBinaryState
    MAX-ACCESS read-only
    STATUS current
    DESCRIPTION "miniENV boolean variable 28."
    ::= { miniENVBooleanVariables 128 }

miniENVBOOL29 OBJECT-TYPE
    SYNTAX StrataonBinaryState
    MAX-ACCESS read-only
    STATUS current
    DESCRIPTION "miniENV boolean variable 29."
    ::= { miniENVBooleanVariables 129 }

miniENVBOOL30 OBJECT-TYPE
    SYNTAX StrataonBinaryState
    MAX-ACCESS read-only
    STATUS current
    DESCRIPTION "miniENV boolean variable 30."
    ::= { miniENVBooleanVariables 130 }

miniENVBOOL31 OBJECT-TYPE
    SYNTAX StrataonBinaryState
    MAX-ACCESS read-only
    STATUS current
    DESCRIPTION "miniENV boolean variable 31."
    ::= { miniENVBooleanVariables 131 }

miniENVBOOL32 OBJECT-TYPE
    SYNTAX StrataonBinaryState
    MAX-ACCESS read-only
    STATUS current
    DESCRIPTION "miniENV boolean variable 32."
    ::= { miniENVBooleanVariables 132 }

-- miniENV long variables 01..32 (subidentifiers 101..132)

miniENVLONG01 OBJECT-TYPE
    SYNTAX Integer32
    MAX-ACCESS read-only
    STATUS current
    DESCRIPTION "miniENV long variable 01."
    ::= { miniENVLongVariables 101 }

miniENVLONG02 OBJECT-TYPE
    SYNTAX Integer32
    MAX-ACCESS read-only
    STATUS current
    DESCRIPTION "miniENV long variable 02."
    ::= { miniENVLongVariables 102 }

miniENVLONG03 OBJECT-TYPE
    SYNTAX Integer32
    MAX-ACCESS read-only
    STATUS current
    DESCRIPTION "miniENV long variable 03."
    ::= { miniENVLongVariables 103 }

miniENVLONG04 OBJECT-TYPE
    SYNTAX Integer32
    MAX-ACCESS read-only
    STATUS current
    DESCRIPTION "miniENV long variable 04."
    ::= { miniENVLongVariables 104 }

miniENVLONG05 OBJECT-TYPE
    SYNTAX Integer32
    MAX-ACCESS read-only
    STATUS current
    DESCRIPTION "miniENV long variable 05."
    ::= { miniENVLongVariables 105 }

miniENVLONG06 OBJECT-TYPE
    SYNTAX Integer32
    MAX-ACCESS read-only
    STATUS current
    DESCRIPTION "miniENV long variable 06."
    ::= { miniENVLongVariables 106 }

miniENVLONG07 OBJECT-TYPE
    SYNTAX Integer32
    MAX-ACCESS read-only
    STATUS current
    DESCRIPTION "miniENV long variable 07."
    ::= { miniENVLongVariables 107 }

miniENVLONG08 OBJECT-TYPE
    SYNTAX Integer32
    MAX-ACCESS read-only
    STATUS current
    DESCRIPTION "miniENV long variable 08."
    ::= { miniENVLongVariables 108 }

miniENVLONG09 OBJECT-TYPE
    SYNTAX Integer32
    MAX-ACCESS read-only
    STATUS current
    DESCRIPTION "miniENV long variable 09."
    ::= { miniENVLongVariables 109 }

miniENVLONG10 OBJECT-TYPE
    SYNTAX Integer32
    MAX-ACCESS read-only
    STATUS current
    DESCRIPTION "miniENV long variable 10."
    ::= { miniENVLongVariables 110 }

miniENVLONG11 OBJECT-TYPE
    SYNTAX Integer32
    MAX-ACCESS read-only
    STATUS current
    DESCRIPTION "miniENV long variable 11."
    ::= { miniENVLongVariables 111 }

miniENVLONG12 OBJECT-TYPE
    SYNTAX Integer32
    MAX-ACCESS read-only
    STATUS current
    DESCRIPTION "miniENV long variable 12."
    ::= { miniENVLongVariables 112 }

miniENVLONG13 OBJECT-TYPE
    SYNTAX Integer32
    MAX-ACCESS read-only
    STATUS current
    DESCRIPTION "miniENV long variable 13."
    ::= { miniENVLongVariables 113 }

miniENVLONG14 OBJECT-TYPE
    SYNTAX Integer32
    MAX-ACCESS read-only
    STATUS current
    DESCRIPTION "miniENV long variable 14."
    ::= { miniENVLongVariables 114 }

miniENVLONG15 OBJECT-TYPE
    SYNTAX Integer32
    MAX-ACCESS read-only
    STATUS current
    DESCRIPTION "miniENV long variable 15."
    ::= { miniENVLongVariables 115 }

miniENVLONG16 OBJECT-TYPE
    SYNTAX Integer32
    MAX-ACCESS read-only
    STATUS current
    DESCRIPTION "miniENV long variable 16."
    ::= { miniENVLongVariables 116 }

miniENVLONG17 OBJECT-TYPE
    SYNTAX Integer32
    MAX-ACCESS read-only
    STATUS current
    DESCRIPTION "miniENV long variable 17."
    ::= { miniENVLongVariables 117 }

miniENVLONG18 OBJECT-TYPE
    SYNTAX Integer32
    MAX-ACCESS read-only
    STATUS current
    DESCRIPTION "miniENV long variable 18."
    ::= { miniENVLongVariables 118 }

miniENVLONG19 OBJECT-TYPE
    SYNTAX Integer32
    MAX-ACCESS read-only
    STATUS current
    DESCRIPTION "miniENV long variable 19."
    ::= { miniENVLongVariables 119 }

miniENVLONG20 OBJECT-TYPE
    SYNTAX Integer32
    MAX-ACCESS read-only
    STATUS current
    DESCRIPTION "miniENV long variable 20."
    ::= { miniENVLongVariables 120 }

miniENVLONG21 OBJECT-TYPE
    SYNTAX Integer32
    MAX-ACCESS read-only
    STATUS current
    DESCRIPTION "miniENV long variable 21."
    ::= { miniENVLongVariables 121 }

miniENVLONG22 OBJECT-TYPE
    SYNTAX Integer32
    MAX-ACCESS read-only
    STATUS current
    DESCRIPTION "miniENV long variable 22."
    ::= { miniENVLongVariables 122 }

miniENVLONG23 OBJECT-TYPE
    SYNTAX Integer32
    MAX-ACCESS read-only
    STATUS current
    DESCRIPTION "miniENV long variable 23."
    ::= { miniENVLongVariables 123 }

miniENVLONG24 OBJECT-TYPE
    SYNTAX Integer32
    MAX-ACCESS read-only
    STATUS current
    DESCRIPTION "miniENV long variable 24."
    ::= { miniENVLongVariables 124 }

miniENVLONG25 OBJECT-TYPE
    SYNTAX Integer32
    MAX-ACCESS read-only
    STATUS current
    DESCRIPTION "miniENV long variable 25."
    ::= { miniENVLongVariables 125 }

miniENVLONG26 OBJECT-TYPE
    SYNTAX Integer32
    MAX-ACCESS read-only
    STATUS current
    DESCRIPTION "miniENV long variable 26."
    ::= { miniENVLongVariables 126 }

miniENVLONG27 OBJECT-TYPE
    SYNTAX Integer32
    MAX-ACCESS read-only
    STATUS current
    DESCRIPTION "miniENV long variable 27."
    ::= { miniENVLongVariables 127 }

miniENVLONG28 OBJECT-TYPE
    SYNTAX Integer32
    MAX-ACCESS read-only
    STATUS current
    DESCRIPTION "miniENV long variable 28."
    ::= { miniENVLongVariables 128 }

miniENVLONG29 OBJECT-TYPE
    SYNTAX Integer32
    MAX-ACCESS read-only
    STATUS current
    DESCRIPTION "miniENV long variable 29."
    ::= { miniENVLongVariables 129 }

miniENVLONG30 OBJECT-TYPE
    SYNTAX Integer32
    MAX-ACCESS read-only
    STATUS current
    DESCRIPTION "miniENV long variable 30."
    ::= { miniENVLongVariables 130 }

miniENVLONG31 OBJECT-TYPE
    SYNTAX Integer32
    MAX-ACCESS read-only
    STATUS current
    DESCRIPTION "miniENV long variable 31."
    ::= { miniENVLongVariables 131 }

miniENVLONG32 OBJECT-TYPE
    SYNTAX Integer32
    MAX-ACCESS read-only
    STATUS current
    DESCRIPTION "miniENV long variable 32."
    ::= { miniENVLongVariables 132 }

-- miniENV environmental analog inputs (subidentifiers 101..108)

miniENVTEMP01 OBJECT-TYPE
    SYNTAX Integer32
    UNITS "degrees Celsius x10"
    MAX-ACCESS read-only
    STATUS current
    DESCRIPTION "miniENV temperature input 01, signed value in tenths of a degree Celsius."
    ::= { miniENVAnalogInputs 101 }

miniENVTEMP02 OBJECT-TYPE
    SYNTAX Integer32
    UNITS "degrees Celsius x10"
    MAX-ACCESS read-only
    STATUS current
    DESCRIPTION "miniENV temperature input 02, signed value in tenths of a degree Celsius."
    ::= { miniENVAnalogInputs 102 }

miniENVTEMP03 OBJECT-TYPE
    SYNTAX Integer32
    UNITS "degrees Celsius x10"
    MAX-ACCESS read-only
    STATUS current
    DESCRIPTION "miniENV temperature input 03, signed value in tenths of a degree Celsius."
    ::= { miniENVAnalogInputs 103 }

miniENVTEMP04 OBJECT-TYPE
    SYNTAX Integer32
    UNITS "degrees Celsius x10"
    MAX-ACCESS read-only
    STATUS current
    DESCRIPTION "miniENV temperature input 04, signed value in tenths of a degree Celsius."
    ::= { miniENVAnalogInputs 104 }

miniENVTEMP05 OBJECT-TYPE
    SYNTAX Integer32
    UNITS "degrees Celsius x10"
    MAX-ACCESS read-only
    STATUS current
    DESCRIPTION "miniENV temperature input 05, signed value in tenths of a degree Celsius."
    ::= { miniENVAnalogInputs 105 }

miniENVHUM01 OBJECT-TYPE
    SYNTAX Gauge32
    UNITS "percent RH x10"
    MAX-ACCESS read-only
    STATUS current
    DESCRIPTION "miniENV relative humidity input 01, value in tenths of percent."
    ::= { miniENVAnalogInputs 106 }

miniENVHUM02 OBJECT-TYPE
    SYNTAX Gauge32
    UNITS "percent RH x10"
    MAX-ACCESS read-only
    STATUS current
    DESCRIPTION "miniENV relative humidity input 02, value in tenths of percent."
    ::= { miniENVAnalogInputs 107 }

miniENVCO201 OBJECT-TYPE
    SYNTAX Gauge32
    UNITS "ppm"
    MAX-ACCESS read-only
    STATUS current
    DESCRIPTION "miniENV carbon dioxide input 01, value directly in ppm."
    ::= { miniENVAnalogInputs 108 }


-- =============================================================
-- =============================================================
-- sentiaMAN branches: 1.3.6.1.4.1.66204.10.4
-- =============================================================

sentiaMANStationCount OBJECT-TYPE
    SYNTAX Integer32 (0..32)
    MAX-ACCESS read-only
    STATUS current
    DESCRIPTION
        "Number of subordinate station slots exposed by sentiaMAN."
    ::= { strataonSentiaMAN 1 }

sentiaMANStationNodes OBJECT-IDENTITY
    STATUS current
    DESCRIPTION
        "sentiaMAN subordinate station Node values. Station 01 uses
         subidentifier 101 and station 32 uses subidentifier 132."
    ::= { strataonSentiaMAN 2 }

sentiaMANStationNode01 OBJECT-TYPE
    SYNTAX Integer32 (1..32)
    MAX-ACCESS read-only
    STATUS current
    DESCRIPTION
        "Subordinate station node number. Station 01."
    ::= { sentiaMANStationNodes 101 }

sentiaMANStationNode02 OBJECT-TYPE
    SYNTAX Integer32 (1..32)
    MAX-ACCESS read-only
    STATUS current
    DESCRIPTION
        "Subordinate station node number. Station 02."
    ::= { sentiaMANStationNodes 102 }

sentiaMANStationNode03 OBJECT-TYPE
    SYNTAX Integer32 (1..32)
    MAX-ACCESS read-only
    STATUS current
    DESCRIPTION
        "Subordinate station node number. Station 03."
    ::= { sentiaMANStationNodes 103 }

sentiaMANStationNode04 OBJECT-TYPE
    SYNTAX Integer32 (1..32)
    MAX-ACCESS read-only
    STATUS current
    DESCRIPTION
        "Subordinate station node number. Station 04."
    ::= { sentiaMANStationNodes 104 }

sentiaMANStationNode05 OBJECT-TYPE
    SYNTAX Integer32 (1..32)
    MAX-ACCESS read-only
    STATUS current
    DESCRIPTION
        "Subordinate station node number. Station 05."
    ::= { sentiaMANStationNodes 105 }

sentiaMANStationNode06 OBJECT-TYPE
    SYNTAX Integer32 (1..32)
    MAX-ACCESS read-only
    STATUS current
    DESCRIPTION
        "Subordinate station node number. Station 06."
    ::= { sentiaMANStationNodes 106 }

sentiaMANStationNode07 OBJECT-TYPE
    SYNTAX Integer32 (1..32)
    MAX-ACCESS read-only
    STATUS current
    DESCRIPTION
        "Subordinate station node number. Station 07."
    ::= { sentiaMANStationNodes 107 }

sentiaMANStationNode08 OBJECT-TYPE
    SYNTAX Integer32 (1..32)
    MAX-ACCESS read-only
    STATUS current
    DESCRIPTION
        "Subordinate station node number. Station 08."
    ::= { sentiaMANStationNodes 108 }

sentiaMANStationNode09 OBJECT-TYPE
    SYNTAX Integer32 (1..32)
    MAX-ACCESS read-only
    STATUS current
    DESCRIPTION
        "Subordinate station node number. Station 09."
    ::= { sentiaMANStationNodes 109 }

sentiaMANStationNode10 OBJECT-TYPE
    SYNTAX Integer32 (1..32)
    MAX-ACCESS read-only
    STATUS current
    DESCRIPTION
        "Subordinate station node number. Station 10."
    ::= { sentiaMANStationNodes 110 }

sentiaMANStationNode11 OBJECT-TYPE
    SYNTAX Integer32 (1..32)
    MAX-ACCESS read-only
    STATUS current
    DESCRIPTION
        "Subordinate station node number. Station 11."
    ::= { sentiaMANStationNodes 111 }

sentiaMANStationNode12 OBJECT-TYPE
    SYNTAX Integer32 (1..32)
    MAX-ACCESS read-only
    STATUS current
    DESCRIPTION
        "Subordinate station node number. Station 12."
    ::= { sentiaMANStationNodes 112 }

sentiaMANStationNode13 OBJECT-TYPE
    SYNTAX Integer32 (1..32)
    MAX-ACCESS read-only
    STATUS current
    DESCRIPTION
        "Subordinate station node number. Station 13."
    ::= { sentiaMANStationNodes 113 }

sentiaMANStationNode14 OBJECT-TYPE
    SYNTAX Integer32 (1..32)
    MAX-ACCESS read-only
    STATUS current
    DESCRIPTION
        "Subordinate station node number. Station 14."
    ::= { sentiaMANStationNodes 114 }

sentiaMANStationNode15 OBJECT-TYPE
    SYNTAX Integer32 (1..32)
    MAX-ACCESS read-only
    STATUS current
    DESCRIPTION
        "Subordinate station node number. Station 15."
    ::= { sentiaMANStationNodes 115 }

sentiaMANStationNode16 OBJECT-TYPE
    SYNTAX Integer32 (1..32)
    MAX-ACCESS read-only
    STATUS current
    DESCRIPTION
        "Subordinate station node number. Station 16."
    ::= { sentiaMANStationNodes 116 }

sentiaMANStationNode17 OBJECT-TYPE
    SYNTAX Integer32 (1..32)
    MAX-ACCESS read-only
    STATUS current
    DESCRIPTION
        "Subordinate station node number. Station 17."
    ::= { sentiaMANStationNodes 117 }

sentiaMANStationNode18 OBJECT-TYPE
    SYNTAX Integer32 (1..32)
    MAX-ACCESS read-only
    STATUS current
    DESCRIPTION
        "Subordinate station node number. Station 18."
    ::= { sentiaMANStationNodes 118 }

sentiaMANStationNode19 OBJECT-TYPE
    SYNTAX Integer32 (1..32)
    MAX-ACCESS read-only
    STATUS current
    DESCRIPTION
        "Subordinate station node number. Station 19."
    ::= { sentiaMANStationNodes 119 }

sentiaMANStationNode20 OBJECT-TYPE
    SYNTAX Integer32 (1..32)
    MAX-ACCESS read-only
    STATUS current
    DESCRIPTION
        "Subordinate station node number. Station 20."
    ::= { sentiaMANStationNodes 120 }

sentiaMANStationNode21 OBJECT-TYPE
    SYNTAX Integer32 (1..32)
    MAX-ACCESS read-only
    STATUS current
    DESCRIPTION
        "Subordinate station node number. Station 21."
    ::= { sentiaMANStationNodes 121 }

sentiaMANStationNode22 OBJECT-TYPE
    SYNTAX Integer32 (1..32)
    MAX-ACCESS read-only
    STATUS current
    DESCRIPTION
        "Subordinate station node number. Station 22."
    ::= { sentiaMANStationNodes 122 }

sentiaMANStationNode23 OBJECT-TYPE
    SYNTAX Integer32 (1..32)
    MAX-ACCESS read-only
    STATUS current
    DESCRIPTION
        "Subordinate station node number. Station 23."
    ::= { sentiaMANStationNodes 123 }

sentiaMANStationNode24 OBJECT-TYPE
    SYNTAX Integer32 (1..32)
    MAX-ACCESS read-only
    STATUS current
    DESCRIPTION
        "Subordinate station node number. Station 24."
    ::= { sentiaMANStationNodes 124 }

sentiaMANStationNode25 OBJECT-TYPE
    SYNTAX Integer32 (1..32)
    MAX-ACCESS read-only
    STATUS current
    DESCRIPTION
        "Subordinate station node number. Station 25."
    ::= { sentiaMANStationNodes 125 }

sentiaMANStationNode26 OBJECT-TYPE
    SYNTAX Integer32 (1..32)
    MAX-ACCESS read-only
    STATUS current
    DESCRIPTION
        "Subordinate station node number. Station 26."
    ::= { sentiaMANStationNodes 126 }

sentiaMANStationNode27 OBJECT-TYPE
    SYNTAX Integer32 (1..32)
    MAX-ACCESS read-only
    STATUS current
    DESCRIPTION
        "Subordinate station node number. Station 27."
    ::= { sentiaMANStationNodes 127 }

sentiaMANStationNode28 OBJECT-TYPE
    SYNTAX Integer32 (1..32)
    MAX-ACCESS read-only
    STATUS current
    DESCRIPTION
        "Subordinate station node number. Station 28."
    ::= { sentiaMANStationNodes 128 }

sentiaMANStationNode29 OBJECT-TYPE
    SYNTAX Integer32 (1..32)
    MAX-ACCESS read-only
    STATUS current
    DESCRIPTION
        "Subordinate station node number. Station 29."
    ::= { sentiaMANStationNodes 129 }

sentiaMANStationNode30 OBJECT-TYPE
    SYNTAX Integer32 (1..32)
    MAX-ACCESS read-only
    STATUS current
    DESCRIPTION
        "Subordinate station node number. Station 30."
    ::= { sentiaMANStationNodes 130 }

sentiaMANStationNode31 OBJECT-TYPE
    SYNTAX Integer32 (1..32)
    MAX-ACCESS read-only
    STATUS current
    DESCRIPTION
        "Subordinate station node number. Station 31."
    ::= { sentiaMANStationNodes 131 }

sentiaMANStationNode32 OBJECT-TYPE
    SYNTAX Integer32 (1..32)
    MAX-ACCESS read-only
    STATUS current
    DESCRIPTION
        "Subordinate station node number. Station 32."
    ::= { sentiaMANStationNodes 132 }

sentiaMANStationNames OBJECT-IDENTITY
    STATUS current
    DESCRIPTION
        "sentiaMAN subordinate station Name values. Station 01 uses
         subidentifier 101 and station 32 uses subidentifier 132."
    ::= { strataonSentiaMAN 3 }

sentiaMANStationName01 OBJECT-TYPE
    SYNTAX DisplayString (SIZE (0..31))
    MAX-ACCESS read-only
    STATUS current
    DESCRIPTION
        "Configured subordinate station name. Station 01."
    ::= { sentiaMANStationNames 101 }

sentiaMANStationName02 OBJECT-TYPE
    SYNTAX DisplayString (SIZE (0..31))
    MAX-ACCESS read-only
    STATUS current
    DESCRIPTION
        "Configured subordinate station name. Station 02."
    ::= { sentiaMANStationNames 102 }

sentiaMANStationName03 OBJECT-TYPE
    SYNTAX DisplayString (SIZE (0..31))
    MAX-ACCESS read-only
    STATUS current
    DESCRIPTION
        "Configured subordinate station name. Station 03."
    ::= { sentiaMANStationNames 103 }

sentiaMANStationName04 OBJECT-TYPE
    SYNTAX DisplayString (SIZE (0..31))
    MAX-ACCESS read-only
    STATUS current
    DESCRIPTION
        "Configured subordinate station name. Station 04."
    ::= { sentiaMANStationNames 104 }

sentiaMANStationName05 OBJECT-TYPE
    SYNTAX DisplayString (SIZE (0..31))
    MAX-ACCESS read-only
    STATUS current
    DESCRIPTION
        "Configured subordinate station name. Station 05."
    ::= { sentiaMANStationNames 105 }

sentiaMANStationName06 OBJECT-TYPE
    SYNTAX DisplayString (SIZE (0..31))
    MAX-ACCESS read-only
    STATUS current
    DESCRIPTION
        "Configured subordinate station name. Station 06."
    ::= { sentiaMANStationNames 106 }

sentiaMANStationName07 OBJECT-TYPE
    SYNTAX DisplayString (SIZE (0..31))
    MAX-ACCESS read-only
    STATUS current
    DESCRIPTION
        "Configured subordinate station name. Station 07."
    ::= { sentiaMANStationNames 107 }

sentiaMANStationName08 OBJECT-TYPE
    SYNTAX DisplayString (SIZE (0..31))
    MAX-ACCESS read-only
    STATUS current
    DESCRIPTION
        "Configured subordinate station name. Station 08."
    ::= { sentiaMANStationNames 108 }

sentiaMANStationName09 OBJECT-TYPE
    SYNTAX DisplayString (SIZE (0..31))
    MAX-ACCESS read-only
    STATUS current
    DESCRIPTION
        "Configured subordinate station name. Station 09."
    ::= { sentiaMANStationNames 109 }

sentiaMANStationName10 OBJECT-TYPE
    SYNTAX DisplayString (SIZE (0..31))
    MAX-ACCESS read-only
    STATUS current
    DESCRIPTION
        "Configured subordinate station name. Station 10."
    ::= { sentiaMANStationNames 110 }

sentiaMANStationName11 OBJECT-TYPE
    SYNTAX DisplayString (SIZE (0..31))
    MAX-ACCESS read-only
    STATUS current
    DESCRIPTION
        "Configured subordinate station name. Station 11."
    ::= { sentiaMANStationNames 111 }

sentiaMANStationName12 OBJECT-TYPE
    SYNTAX DisplayString (SIZE (0..31))
    MAX-ACCESS read-only
    STATUS current
    DESCRIPTION
        "Configured subordinate station name. Station 12."
    ::= { sentiaMANStationNames 112 }

sentiaMANStationName13 OBJECT-TYPE
    SYNTAX DisplayString (SIZE (0..31))
    MAX-ACCESS read-only
    STATUS current
    DESCRIPTION
        "Configured subordinate station name. Station 13."
    ::= { sentiaMANStationNames 113 }

sentiaMANStationName14 OBJECT-TYPE
    SYNTAX DisplayString (SIZE (0..31))
    MAX-ACCESS read-only
    STATUS current
    DESCRIPTION
        "Configured subordinate station name. Station 14."
    ::= { sentiaMANStationNames 114 }

sentiaMANStationName15 OBJECT-TYPE
    SYNTAX DisplayString (SIZE (0..31))
    MAX-ACCESS read-only
    STATUS current
    DESCRIPTION
        "Configured subordinate station name. Station 15."
    ::= { sentiaMANStationNames 115 }

sentiaMANStationName16 OBJECT-TYPE
    SYNTAX DisplayString (SIZE (0..31))
    MAX-ACCESS read-only
    STATUS current
    DESCRIPTION
        "Configured subordinate station name. Station 16."
    ::= { sentiaMANStationNames 116 }

sentiaMANStationName17 OBJECT-TYPE
    SYNTAX DisplayString (SIZE (0..31))
    MAX-ACCESS read-only
    STATUS current
    DESCRIPTION
        "Configured subordinate station name. Station 17."
    ::= { sentiaMANStationNames 117 }

sentiaMANStationName18 OBJECT-TYPE
    SYNTAX DisplayString (SIZE (0..31))
    MAX-ACCESS read-only
    STATUS current
    DESCRIPTION
        "Configured subordinate station name. Station 18."
    ::= { sentiaMANStationNames 118 }

sentiaMANStationName19 OBJECT-TYPE
    SYNTAX DisplayString (SIZE (0..31))
    MAX-ACCESS read-only
    STATUS current
    DESCRIPTION
        "Configured subordinate station name. Station 19."
    ::= { sentiaMANStationNames 119 }

sentiaMANStationName20 OBJECT-TYPE
    SYNTAX DisplayString (SIZE (0..31))
    MAX-ACCESS read-only
    STATUS current
    DESCRIPTION
        "Configured subordinate station name. Station 20."
    ::= { sentiaMANStationNames 120 }

sentiaMANStationName21 OBJECT-TYPE
    SYNTAX DisplayString (SIZE (0..31))
    MAX-ACCESS read-only
    STATUS current
    DESCRIPTION
        "Configured subordinate station name. Station 21."
    ::= { sentiaMANStationNames 121 }

sentiaMANStationName22 OBJECT-TYPE
    SYNTAX DisplayString (SIZE (0..31))
    MAX-ACCESS read-only
    STATUS current
    DESCRIPTION
        "Configured subordinate station name. Station 22."
    ::= { sentiaMANStationNames 122 }

sentiaMANStationName23 OBJECT-TYPE
    SYNTAX DisplayString (SIZE (0..31))
    MAX-ACCESS read-only
    STATUS current
    DESCRIPTION
        "Configured subordinate station name. Station 23."
    ::= { sentiaMANStationNames 123 }

sentiaMANStationName24 OBJECT-TYPE
    SYNTAX DisplayString (SIZE (0..31))
    MAX-ACCESS read-only
    STATUS current
    DESCRIPTION
        "Configured subordinate station name. Station 24."
    ::= { sentiaMANStationNames 124 }

sentiaMANStationName25 OBJECT-TYPE
    SYNTAX DisplayString (SIZE (0..31))
    MAX-ACCESS read-only
    STATUS current
    DESCRIPTION
        "Configured subordinate station name. Station 25."
    ::= { sentiaMANStationNames 125 }

sentiaMANStationName26 OBJECT-TYPE
    SYNTAX DisplayString (SIZE (0..31))
    MAX-ACCESS read-only
    STATUS current
    DESCRIPTION
        "Configured subordinate station name. Station 26."
    ::= { sentiaMANStationNames 126 }

sentiaMANStationName27 OBJECT-TYPE
    SYNTAX DisplayString (SIZE (0..31))
    MAX-ACCESS read-only
    STATUS current
    DESCRIPTION
        "Configured subordinate station name. Station 27."
    ::= { sentiaMANStationNames 127 }

sentiaMANStationName28 OBJECT-TYPE
    SYNTAX DisplayString (SIZE (0..31))
    MAX-ACCESS read-only
    STATUS current
    DESCRIPTION
        "Configured subordinate station name. Station 28."
    ::= { sentiaMANStationNames 128 }

sentiaMANStationName29 OBJECT-TYPE
    SYNTAX DisplayString (SIZE (0..31))
    MAX-ACCESS read-only
    STATUS current
    DESCRIPTION
        "Configured subordinate station name. Station 29."
    ::= { sentiaMANStationNames 129 }

sentiaMANStationName30 OBJECT-TYPE
    SYNTAX DisplayString (SIZE (0..31))
    MAX-ACCESS read-only
    STATUS current
    DESCRIPTION
        "Configured subordinate station name. Station 30."
    ::= { sentiaMANStationNames 130 }

sentiaMANStationName31 OBJECT-TYPE
    SYNTAX DisplayString (SIZE (0..31))
    MAX-ACCESS read-only
    STATUS current
    DESCRIPTION
        "Configured subordinate station name. Station 31."
    ::= { sentiaMANStationNames 131 }

sentiaMANStationName32 OBJECT-TYPE
    SYNTAX DisplayString (SIZE (0..31))
    MAX-ACCESS read-only
    STATUS current
    DESCRIPTION
        "Configured subordinate station name. Station 32."
    ::= { sentiaMANStationNames 132 }

sentiaMANStationCommStatuses OBJECT-IDENTITY
    STATUS current
    DESCRIPTION
        "sentiaMAN subordinate station CommStatus values. Station 01 uses
         subidentifier 101 and station 32 uses subidentifier 132."
    ::= { strataonSentiaMAN 4 }

sentiaMANStationCommStatus01 OBJECT-TYPE
    SYNTAX Integer32 (0..1)
    MAX-ACCESS read-only
    STATUS current
    DESCRIPTION
        "Communication status: 0 = offline, 1 = online. Station 01."
    ::= { sentiaMANStationCommStatuses 101 }

sentiaMANStationCommStatus02 OBJECT-TYPE
    SYNTAX Integer32 (0..1)
    MAX-ACCESS read-only
    STATUS current
    DESCRIPTION
        "Communication status: 0 = offline, 1 = online. Station 02."
    ::= { sentiaMANStationCommStatuses 102 }

sentiaMANStationCommStatus03 OBJECT-TYPE
    SYNTAX Integer32 (0..1)
    MAX-ACCESS read-only
    STATUS current
    DESCRIPTION
        "Communication status: 0 = offline, 1 = online. Station 03."
    ::= { sentiaMANStationCommStatuses 103 }

sentiaMANStationCommStatus04 OBJECT-TYPE
    SYNTAX Integer32 (0..1)
    MAX-ACCESS read-only
    STATUS current
    DESCRIPTION
        "Communication status: 0 = offline, 1 = online. Station 04."
    ::= { sentiaMANStationCommStatuses 104 }

sentiaMANStationCommStatus05 OBJECT-TYPE
    SYNTAX Integer32 (0..1)
    MAX-ACCESS read-only
    STATUS current
    DESCRIPTION
        "Communication status: 0 = offline, 1 = online. Station 05."
    ::= { sentiaMANStationCommStatuses 105 }

sentiaMANStationCommStatus06 OBJECT-TYPE
    SYNTAX Integer32 (0..1)
    MAX-ACCESS read-only
    STATUS current
    DESCRIPTION
        "Communication status: 0 = offline, 1 = online. Station 06."
    ::= { sentiaMANStationCommStatuses 106 }

sentiaMANStationCommStatus07 OBJECT-TYPE
    SYNTAX Integer32 (0..1)
    MAX-ACCESS read-only
    STATUS current
    DESCRIPTION
        "Communication status: 0 = offline, 1 = online. Station 07."
    ::= { sentiaMANStationCommStatuses 107 }

sentiaMANStationCommStatus08 OBJECT-TYPE
    SYNTAX Integer32 (0..1)
    MAX-ACCESS read-only
    STATUS current
    DESCRIPTION
        "Communication status: 0 = offline, 1 = online. Station 08."
    ::= { sentiaMANStationCommStatuses 108 }

sentiaMANStationCommStatus09 OBJECT-TYPE
    SYNTAX Integer32 (0..1)
    MAX-ACCESS read-only
    STATUS current
    DESCRIPTION
        "Communication status: 0 = offline, 1 = online. Station 09."
    ::= { sentiaMANStationCommStatuses 109 }

sentiaMANStationCommStatus10 OBJECT-TYPE
    SYNTAX Integer32 (0..1)
    MAX-ACCESS read-only
    STATUS current
    DESCRIPTION
        "Communication status: 0 = offline, 1 = online. Station 10."
    ::= { sentiaMANStationCommStatuses 110 }

sentiaMANStationCommStatus11 OBJECT-TYPE
    SYNTAX Integer32 (0..1)
    MAX-ACCESS read-only
    STATUS current
    DESCRIPTION
        "Communication status: 0 = offline, 1 = online. Station 11."
    ::= { sentiaMANStationCommStatuses 111 }

sentiaMANStationCommStatus12 OBJECT-TYPE
    SYNTAX Integer32 (0..1)
    MAX-ACCESS read-only
    STATUS current
    DESCRIPTION
        "Communication status: 0 = offline, 1 = online. Station 12."
    ::= { sentiaMANStationCommStatuses 112 }

sentiaMANStationCommStatus13 OBJECT-TYPE
    SYNTAX Integer32 (0..1)
    MAX-ACCESS read-only
    STATUS current
    DESCRIPTION
        "Communication status: 0 = offline, 1 = online. Station 13."
    ::= { sentiaMANStationCommStatuses 113 }

sentiaMANStationCommStatus14 OBJECT-TYPE
    SYNTAX Integer32 (0..1)
    MAX-ACCESS read-only
    STATUS current
    DESCRIPTION
        "Communication status: 0 = offline, 1 = online. Station 14."
    ::= { sentiaMANStationCommStatuses 114 }

sentiaMANStationCommStatus15 OBJECT-TYPE
    SYNTAX Integer32 (0..1)
    MAX-ACCESS read-only
    STATUS current
    DESCRIPTION
        "Communication status: 0 = offline, 1 = online. Station 15."
    ::= { sentiaMANStationCommStatuses 115 }

sentiaMANStationCommStatus16 OBJECT-TYPE
    SYNTAX Integer32 (0..1)
    MAX-ACCESS read-only
    STATUS current
    DESCRIPTION
        "Communication status: 0 = offline, 1 = online. Station 16."
    ::= { sentiaMANStationCommStatuses 116 }

sentiaMANStationCommStatus17 OBJECT-TYPE
    SYNTAX Integer32 (0..1)
    MAX-ACCESS read-only
    STATUS current
    DESCRIPTION
        "Communication status: 0 = offline, 1 = online. Station 17."
    ::= { sentiaMANStationCommStatuses 117 }

sentiaMANStationCommStatus18 OBJECT-TYPE
    SYNTAX Integer32 (0..1)
    MAX-ACCESS read-only
    STATUS current
    DESCRIPTION
        "Communication status: 0 = offline, 1 = online. Station 18."
    ::= { sentiaMANStationCommStatuses 118 }

sentiaMANStationCommStatus19 OBJECT-TYPE
    SYNTAX Integer32 (0..1)
    MAX-ACCESS read-only
    STATUS current
    DESCRIPTION
        "Communication status: 0 = offline, 1 = online. Station 19."
    ::= { sentiaMANStationCommStatuses 119 }

sentiaMANStationCommStatus20 OBJECT-TYPE
    SYNTAX Integer32 (0..1)
    MAX-ACCESS read-only
    STATUS current
    DESCRIPTION
        "Communication status: 0 = offline, 1 = online. Station 20."
    ::= { sentiaMANStationCommStatuses 120 }

sentiaMANStationCommStatus21 OBJECT-TYPE
    SYNTAX Integer32 (0..1)
    MAX-ACCESS read-only
    STATUS current
    DESCRIPTION
        "Communication status: 0 = offline, 1 = online. Station 21."
    ::= { sentiaMANStationCommStatuses 121 }

sentiaMANStationCommStatus22 OBJECT-TYPE
    SYNTAX Integer32 (0..1)
    MAX-ACCESS read-only
    STATUS current
    DESCRIPTION
        "Communication status: 0 = offline, 1 = online. Station 22."
    ::= { sentiaMANStationCommStatuses 122 }

sentiaMANStationCommStatus23 OBJECT-TYPE
    SYNTAX Integer32 (0..1)
    MAX-ACCESS read-only
    STATUS current
    DESCRIPTION
        "Communication status: 0 = offline, 1 = online. Station 23."
    ::= { sentiaMANStationCommStatuses 123 }

sentiaMANStationCommStatus24 OBJECT-TYPE
    SYNTAX Integer32 (0..1)
    MAX-ACCESS read-only
    STATUS current
    DESCRIPTION
        "Communication status: 0 = offline, 1 = online. Station 24."
    ::= { sentiaMANStationCommStatuses 124 }

sentiaMANStationCommStatus25 OBJECT-TYPE
    SYNTAX Integer32 (0..1)
    MAX-ACCESS read-only
    STATUS current
    DESCRIPTION
        "Communication status: 0 = offline, 1 = online. Station 25."
    ::= { sentiaMANStationCommStatuses 125 }

sentiaMANStationCommStatus26 OBJECT-TYPE
    SYNTAX Integer32 (0..1)
    MAX-ACCESS read-only
    STATUS current
    DESCRIPTION
        "Communication status: 0 = offline, 1 = online. Station 26."
    ::= { sentiaMANStationCommStatuses 126 }

sentiaMANStationCommStatus27 OBJECT-TYPE
    SYNTAX Integer32 (0..1)
    MAX-ACCESS read-only
    STATUS current
    DESCRIPTION
        "Communication status: 0 = offline, 1 = online. Station 27."
    ::= { sentiaMANStationCommStatuses 127 }

sentiaMANStationCommStatus28 OBJECT-TYPE
    SYNTAX Integer32 (0..1)
    MAX-ACCESS read-only
    STATUS current
    DESCRIPTION
        "Communication status: 0 = offline, 1 = online. Station 28."
    ::= { sentiaMANStationCommStatuses 128 }

sentiaMANStationCommStatus29 OBJECT-TYPE
    SYNTAX Integer32 (0..1)
    MAX-ACCESS read-only
    STATUS current
    DESCRIPTION
        "Communication status: 0 = offline, 1 = online. Station 29."
    ::= { sentiaMANStationCommStatuses 129 }

sentiaMANStationCommStatus30 OBJECT-TYPE
    SYNTAX Integer32 (0..1)
    MAX-ACCESS read-only
    STATUS current
    DESCRIPTION
        "Communication status: 0 = offline, 1 = online. Station 30."
    ::= { sentiaMANStationCommStatuses 130 }

sentiaMANStationCommStatus31 OBJECT-TYPE
    SYNTAX Integer32 (0..1)
    MAX-ACCESS read-only
    STATUS current
    DESCRIPTION
        "Communication status: 0 = offline, 1 = online. Station 31."
    ::= { sentiaMANStationCommStatuses 131 }

sentiaMANStationCommStatus32 OBJECT-TYPE
    SYNTAX Integer32 (0..1)
    MAX-ACCESS read-only
    STATUS current
    DESCRIPTION
        "Communication status: 0 = offline, 1 = online. Station 32."
    ::= { sentiaMANStationCommStatuses 132 }

sentiaMANStationFirmwares OBJECT-IDENTITY
    STATUS current
    DESCRIPTION
        "sentiaMAN subordinate station Firmware values. Station 01 uses
         subidentifier 101 and station 32 uses subidentifier 132."
    ::= { strataonSentiaMAN 5 }

sentiaMANStationFirmware01 OBJECT-TYPE
    SYNTAX DisplayString (SIZE (0..15))
    MAX-ACCESS read-only
    STATUS current
    DESCRIPTION
        "Firmware version reported by the subordinate station. Station 01."
    ::= { sentiaMANStationFirmwares 101 }

sentiaMANStationFirmware02 OBJECT-TYPE
    SYNTAX DisplayString (SIZE (0..15))
    MAX-ACCESS read-only
    STATUS current
    DESCRIPTION
        "Firmware version reported by the subordinate station. Station 02."
    ::= { sentiaMANStationFirmwares 102 }

sentiaMANStationFirmware03 OBJECT-TYPE
    SYNTAX DisplayString (SIZE (0..15))
    MAX-ACCESS read-only
    STATUS current
    DESCRIPTION
        "Firmware version reported by the subordinate station. Station 03."
    ::= { sentiaMANStationFirmwares 103 }

sentiaMANStationFirmware04 OBJECT-TYPE
    SYNTAX DisplayString (SIZE (0..15))
    MAX-ACCESS read-only
    STATUS current
    DESCRIPTION
        "Firmware version reported by the subordinate station. Station 04."
    ::= { sentiaMANStationFirmwares 104 }

sentiaMANStationFirmware05 OBJECT-TYPE
    SYNTAX DisplayString (SIZE (0..15))
    MAX-ACCESS read-only
    STATUS current
    DESCRIPTION
        "Firmware version reported by the subordinate station. Station 05."
    ::= { sentiaMANStationFirmwares 105 }

sentiaMANStationFirmware06 OBJECT-TYPE
    SYNTAX DisplayString (SIZE (0..15))
    MAX-ACCESS read-only
    STATUS current
    DESCRIPTION
        "Firmware version reported by the subordinate station. Station 06."
    ::= { sentiaMANStationFirmwares 106 }

sentiaMANStationFirmware07 OBJECT-TYPE
    SYNTAX DisplayString (SIZE (0..15))
    MAX-ACCESS read-only
    STATUS current
    DESCRIPTION
        "Firmware version reported by the subordinate station. Station 07."
    ::= { sentiaMANStationFirmwares 107 }

sentiaMANStationFirmware08 OBJECT-TYPE
    SYNTAX DisplayString (SIZE (0..15))
    MAX-ACCESS read-only
    STATUS current
    DESCRIPTION
        "Firmware version reported by the subordinate station. Station 08."
    ::= { sentiaMANStationFirmwares 108 }

sentiaMANStationFirmware09 OBJECT-TYPE
    SYNTAX DisplayString (SIZE (0..15))
    MAX-ACCESS read-only
    STATUS current
    DESCRIPTION
        "Firmware version reported by the subordinate station. Station 09."
    ::= { sentiaMANStationFirmwares 109 }

sentiaMANStationFirmware10 OBJECT-TYPE
    SYNTAX DisplayString (SIZE (0..15))
    MAX-ACCESS read-only
    STATUS current
    DESCRIPTION
        "Firmware version reported by the subordinate station. Station 10."
    ::= { sentiaMANStationFirmwares 110 }

sentiaMANStationFirmware11 OBJECT-TYPE
    SYNTAX DisplayString (SIZE (0..15))
    MAX-ACCESS read-only
    STATUS current
    DESCRIPTION
        "Firmware version reported by the subordinate station. Station 11."
    ::= { sentiaMANStationFirmwares 111 }

sentiaMANStationFirmware12 OBJECT-TYPE
    SYNTAX DisplayString (SIZE (0..15))
    MAX-ACCESS read-only
    STATUS current
    DESCRIPTION
        "Firmware version reported by the subordinate station. Station 12."
    ::= { sentiaMANStationFirmwares 112 }

sentiaMANStationFirmware13 OBJECT-TYPE
    SYNTAX DisplayString (SIZE (0..15))
    MAX-ACCESS read-only
    STATUS current
    DESCRIPTION
        "Firmware version reported by the subordinate station. Station 13."
    ::= { sentiaMANStationFirmwares 113 }

sentiaMANStationFirmware14 OBJECT-TYPE
    SYNTAX DisplayString (SIZE (0..15))
    MAX-ACCESS read-only
    STATUS current
    DESCRIPTION
        "Firmware version reported by the subordinate station. Station 14."
    ::= { sentiaMANStationFirmwares 114 }

sentiaMANStationFirmware15 OBJECT-TYPE
    SYNTAX DisplayString (SIZE (0..15))
    MAX-ACCESS read-only
    STATUS current
    DESCRIPTION
        "Firmware version reported by the subordinate station. Station 15."
    ::= { sentiaMANStationFirmwares 115 }

sentiaMANStationFirmware16 OBJECT-TYPE
    SYNTAX DisplayString (SIZE (0..15))
    MAX-ACCESS read-only
    STATUS current
    DESCRIPTION
        "Firmware version reported by the subordinate station. Station 16."
    ::= { sentiaMANStationFirmwares 116 }

sentiaMANStationFirmware17 OBJECT-TYPE
    SYNTAX DisplayString (SIZE (0..15))
    MAX-ACCESS read-only
    STATUS current
    DESCRIPTION
        "Firmware version reported by the subordinate station. Station 17."
    ::= { sentiaMANStationFirmwares 117 }

sentiaMANStationFirmware18 OBJECT-TYPE
    SYNTAX DisplayString (SIZE (0..15))
    MAX-ACCESS read-only
    STATUS current
    DESCRIPTION
        "Firmware version reported by the subordinate station. Station 18."
    ::= { sentiaMANStationFirmwares 118 }

sentiaMANStationFirmware19 OBJECT-TYPE
    SYNTAX DisplayString (SIZE (0..15))
    MAX-ACCESS read-only
    STATUS current
    DESCRIPTION
        "Firmware version reported by the subordinate station. Station 19."
    ::= { sentiaMANStationFirmwares 119 }

sentiaMANStationFirmware20 OBJECT-TYPE
    SYNTAX DisplayString (SIZE (0..15))
    MAX-ACCESS read-only
    STATUS current
    DESCRIPTION
        "Firmware version reported by the subordinate station. Station 20."
    ::= { sentiaMANStationFirmwares 120 }

sentiaMANStationFirmware21 OBJECT-TYPE
    SYNTAX DisplayString (SIZE (0..15))
    MAX-ACCESS read-only
    STATUS current
    DESCRIPTION
        "Firmware version reported by the subordinate station. Station 21."
    ::= { sentiaMANStationFirmwares 121 }

sentiaMANStationFirmware22 OBJECT-TYPE
    SYNTAX DisplayString (SIZE (0..15))
    MAX-ACCESS read-only
    STATUS current
    DESCRIPTION
        "Firmware version reported by the subordinate station. Station 22."
    ::= { sentiaMANStationFirmwares 122 }

sentiaMANStationFirmware23 OBJECT-TYPE
    SYNTAX DisplayString (SIZE (0..15))
    MAX-ACCESS read-only
    STATUS current
    DESCRIPTION
        "Firmware version reported by the subordinate station. Station 23."
    ::= { sentiaMANStationFirmwares 123 }

sentiaMANStationFirmware24 OBJECT-TYPE
    SYNTAX DisplayString (SIZE (0..15))
    MAX-ACCESS read-only
    STATUS current
    DESCRIPTION
        "Firmware version reported by the subordinate station. Station 24."
    ::= { sentiaMANStationFirmwares 124 }

sentiaMANStationFirmware25 OBJECT-TYPE
    SYNTAX DisplayString (SIZE (0..15))
    MAX-ACCESS read-only
    STATUS current
    DESCRIPTION
        "Firmware version reported by the subordinate station. Station 25."
    ::= { sentiaMANStationFirmwares 125 }

sentiaMANStationFirmware26 OBJECT-TYPE
    SYNTAX DisplayString (SIZE (0..15))
    MAX-ACCESS read-only
    STATUS current
    DESCRIPTION
        "Firmware version reported by the subordinate station. Station 26."
    ::= { sentiaMANStationFirmwares 126 }

sentiaMANStationFirmware27 OBJECT-TYPE
    SYNTAX DisplayString (SIZE (0..15))
    MAX-ACCESS read-only
    STATUS current
    DESCRIPTION
        "Firmware version reported by the subordinate station. Station 27."
    ::= { sentiaMANStationFirmwares 127 }

sentiaMANStationFirmware28 OBJECT-TYPE
    SYNTAX DisplayString (SIZE (0..15))
    MAX-ACCESS read-only
    STATUS current
    DESCRIPTION
        "Firmware version reported by the subordinate station. Station 28."
    ::= { sentiaMANStationFirmwares 128 }

sentiaMANStationFirmware29 OBJECT-TYPE
    SYNTAX DisplayString (SIZE (0..15))
    MAX-ACCESS read-only
    STATUS current
    DESCRIPTION
        "Firmware version reported by the subordinate station. Station 29."
    ::= { sentiaMANStationFirmwares 129 }

sentiaMANStationFirmware30 OBJECT-TYPE
    SYNTAX DisplayString (SIZE (0..15))
    MAX-ACCESS read-only
    STATUS current
    DESCRIPTION
        "Firmware version reported by the subordinate station. Station 30."
    ::= { sentiaMANStationFirmwares 130 }

sentiaMANStationFirmware31 OBJECT-TYPE
    SYNTAX DisplayString (SIZE (0..15))
    MAX-ACCESS read-only
    STATUS current
    DESCRIPTION
        "Firmware version reported by the subordinate station. Station 31."
    ::= { sentiaMANStationFirmwares 131 }

sentiaMANStationFirmware32 OBJECT-TYPE
    SYNTAX DisplayString (SIZE (0..15))
    MAX-ACCESS read-only
    STATUS current
    DESCRIPTION
        "Firmware version reported by the subordinate station. Station 32."
    ::= { sentiaMANStationFirmwares 132 }

sentiaMANStationTemp1Values OBJECT-IDENTITY
    STATUS current
    DESCRIPTION
        "sentiaMAN subordinate station Temp1 values. Station 01 uses
         subidentifier 101 and station 32 uses subidentifier 132."
    ::= { strataonSentiaMAN 6 }

sentiaMANStationTemp101 OBJECT-TYPE
    SYNTAX Integer32
    UNITS "degrees Celsius x10"
    MAX-ACCESS read-only
    STATUS current
    DESCRIPTION
        "Temperature 1, signed value in tenths of a degree Celsius. Station 01."
    ::= { sentiaMANStationTemp1Values 101 }

sentiaMANStationTemp102 OBJECT-TYPE
    SYNTAX Integer32
    UNITS "degrees Celsius x10"
    MAX-ACCESS read-only
    STATUS current
    DESCRIPTION
        "Temperature 1, signed value in tenths of a degree Celsius. Station 02."
    ::= { sentiaMANStationTemp1Values 102 }

sentiaMANStationTemp103 OBJECT-TYPE
    SYNTAX Integer32
    UNITS "degrees Celsius x10"
    MAX-ACCESS read-only
    STATUS current
    DESCRIPTION
        "Temperature 1, signed value in tenths of a degree Celsius. Station 03."
    ::= { sentiaMANStationTemp1Values 103 }

sentiaMANStationTemp104 OBJECT-TYPE
    SYNTAX Integer32
    UNITS "degrees Celsius x10"
    MAX-ACCESS read-only
    STATUS current
    DESCRIPTION
        "Temperature 1, signed value in tenths of a degree Celsius. Station 04."
    ::= { sentiaMANStationTemp1Values 104 }

sentiaMANStationTemp105 OBJECT-TYPE
    SYNTAX Integer32
    UNITS "degrees Celsius x10"
    MAX-ACCESS read-only
    STATUS current
    DESCRIPTION
        "Temperature 1, signed value in tenths of a degree Celsius. Station 05."
    ::= { sentiaMANStationTemp1Values 105 }

sentiaMANStationTemp106 OBJECT-TYPE
    SYNTAX Integer32
    UNITS "degrees Celsius x10"
    MAX-ACCESS read-only
    STATUS current
    DESCRIPTION
        "Temperature 1, signed value in tenths of a degree Celsius. Station 06."
    ::= { sentiaMANStationTemp1Values 106 }

sentiaMANStationTemp107 OBJECT-TYPE
    SYNTAX Integer32
    UNITS "degrees Celsius x10"
    MAX-ACCESS read-only
    STATUS current
    DESCRIPTION
        "Temperature 1, signed value in tenths of a degree Celsius. Station 07."
    ::= { sentiaMANStationTemp1Values 107 }

sentiaMANStationTemp108 OBJECT-TYPE
    SYNTAX Integer32
    UNITS "degrees Celsius x10"
    MAX-ACCESS read-only
    STATUS current
    DESCRIPTION
        "Temperature 1, signed value in tenths of a degree Celsius. Station 08."
    ::= { sentiaMANStationTemp1Values 108 }

sentiaMANStationTemp109 OBJECT-TYPE
    SYNTAX Integer32
    UNITS "degrees Celsius x10"
    MAX-ACCESS read-only
    STATUS current
    DESCRIPTION
        "Temperature 1, signed value in tenths of a degree Celsius. Station 09."
    ::= { sentiaMANStationTemp1Values 109 }

sentiaMANStationTemp110 OBJECT-TYPE
    SYNTAX Integer32
    UNITS "degrees Celsius x10"
    MAX-ACCESS read-only
    STATUS current
    DESCRIPTION
        "Temperature 1, signed value in tenths of a degree Celsius. Station 10."
    ::= { sentiaMANStationTemp1Values 110 }

sentiaMANStationTemp111 OBJECT-TYPE
    SYNTAX Integer32
    UNITS "degrees Celsius x10"
    MAX-ACCESS read-only
    STATUS current
    DESCRIPTION
        "Temperature 1, signed value in tenths of a degree Celsius. Station 11."
    ::= { sentiaMANStationTemp1Values 111 }

sentiaMANStationTemp112 OBJECT-TYPE
    SYNTAX Integer32
    UNITS "degrees Celsius x10"
    MAX-ACCESS read-only
    STATUS current
    DESCRIPTION
        "Temperature 1, signed value in tenths of a degree Celsius. Station 12."
    ::= { sentiaMANStationTemp1Values 112 }

sentiaMANStationTemp113 OBJECT-TYPE
    SYNTAX Integer32
    UNITS "degrees Celsius x10"
    MAX-ACCESS read-only
    STATUS current
    DESCRIPTION
        "Temperature 1, signed value in tenths of a degree Celsius. Station 13."
    ::= { sentiaMANStationTemp1Values 113 }

sentiaMANStationTemp114 OBJECT-TYPE
    SYNTAX Integer32
    UNITS "degrees Celsius x10"
    MAX-ACCESS read-only
    STATUS current
    DESCRIPTION
        "Temperature 1, signed value in tenths of a degree Celsius. Station 14."
    ::= { sentiaMANStationTemp1Values 114 }

sentiaMANStationTemp115 OBJECT-TYPE
    SYNTAX Integer32
    UNITS "degrees Celsius x10"
    MAX-ACCESS read-only
    STATUS current
    DESCRIPTION
        "Temperature 1, signed value in tenths of a degree Celsius. Station 15."
    ::= { sentiaMANStationTemp1Values 115 }

sentiaMANStationTemp116 OBJECT-TYPE
    SYNTAX Integer32
    UNITS "degrees Celsius x10"
    MAX-ACCESS read-only
    STATUS current
    DESCRIPTION
        "Temperature 1, signed value in tenths of a degree Celsius. Station 16."
    ::= { sentiaMANStationTemp1Values 116 }

sentiaMANStationTemp117 OBJECT-TYPE
    SYNTAX Integer32
    UNITS "degrees Celsius x10"
    MAX-ACCESS read-only
    STATUS current
    DESCRIPTION
        "Temperature 1, signed value in tenths of a degree Celsius. Station 17."
    ::= { sentiaMANStationTemp1Values 117 }

sentiaMANStationTemp118 OBJECT-TYPE
    SYNTAX Integer32
    UNITS "degrees Celsius x10"
    MAX-ACCESS read-only
    STATUS current
    DESCRIPTION
        "Temperature 1, signed value in tenths of a degree Celsius. Station 18."
    ::= { sentiaMANStationTemp1Values 118 }

sentiaMANStationTemp119 OBJECT-TYPE
    SYNTAX Integer32
    UNITS "degrees Celsius x10"
    MAX-ACCESS read-only
    STATUS current
    DESCRIPTION
        "Temperature 1, signed value in tenths of a degree Celsius. Station 19."
    ::= { sentiaMANStationTemp1Values 119 }

sentiaMANStationTemp120 OBJECT-TYPE
    SYNTAX Integer32
    UNITS "degrees Celsius x10"
    MAX-ACCESS read-only
    STATUS current
    DESCRIPTION
        "Temperature 1, signed value in tenths of a degree Celsius. Station 20."
    ::= { sentiaMANStationTemp1Values 120 }

sentiaMANStationTemp121 OBJECT-TYPE
    SYNTAX Integer32
    UNITS "degrees Celsius x10"
    MAX-ACCESS read-only
    STATUS current
    DESCRIPTION
        "Temperature 1, signed value in tenths of a degree Celsius. Station 21."
    ::= { sentiaMANStationTemp1Values 121 }

sentiaMANStationTemp122 OBJECT-TYPE
    SYNTAX Integer32
    UNITS "degrees Celsius x10"
    MAX-ACCESS read-only
    STATUS current
    DESCRIPTION
        "Temperature 1, signed value in tenths of a degree Celsius. Station 22."
    ::= { sentiaMANStationTemp1Values 122 }

sentiaMANStationTemp123 OBJECT-TYPE
    SYNTAX Integer32
    UNITS "degrees Celsius x10"
    MAX-ACCESS read-only
    STATUS current
    DESCRIPTION
        "Temperature 1, signed value in tenths of a degree Celsius. Station 23."
    ::= { sentiaMANStationTemp1Values 123 }

sentiaMANStationTemp124 OBJECT-TYPE
    SYNTAX Integer32
    UNITS "degrees Celsius x10"
    MAX-ACCESS read-only
    STATUS current
    DESCRIPTION
        "Temperature 1, signed value in tenths of a degree Celsius. Station 24."
    ::= { sentiaMANStationTemp1Values 124 }

sentiaMANStationTemp125 OBJECT-TYPE
    SYNTAX Integer32
    UNITS "degrees Celsius x10"
    MAX-ACCESS read-only
    STATUS current
    DESCRIPTION
        "Temperature 1, signed value in tenths of a degree Celsius. Station 25."
    ::= { sentiaMANStationTemp1Values 125 }

sentiaMANStationTemp126 OBJECT-TYPE
    SYNTAX Integer32
    UNITS "degrees Celsius x10"
    MAX-ACCESS read-only
    STATUS current
    DESCRIPTION
        "Temperature 1, signed value in tenths of a degree Celsius. Station 26."
    ::= { sentiaMANStationTemp1Values 126 }

sentiaMANStationTemp127 OBJECT-TYPE
    SYNTAX Integer32
    UNITS "degrees Celsius x10"
    MAX-ACCESS read-only
    STATUS current
    DESCRIPTION
        "Temperature 1, signed value in tenths of a degree Celsius. Station 27."
    ::= { sentiaMANStationTemp1Values 127 }

sentiaMANStationTemp128 OBJECT-TYPE
    SYNTAX Integer32
    UNITS "degrees Celsius x10"
    MAX-ACCESS read-only
    STATUS current
    DESCRIPTION
        "Temperature 1, signed value in tenths of a degree Celsius. Station 28."
    ::= { sentiaMANStationTemp1Values 128 }

sentiaMANStationTemp129 OBJECT-TYPE
    SYNTAX Integer32
    UNITS "degrees Celsius x10"
    MAX-ACCESS read-only
    STATUS current
    DESCRIPTION
        "Temperature 1, signed value in tenths of a degree Celsius. Station 29."
    ::= { sentiaMANStationTemp1Values 129 }

sentiaMANStationTemp130 OBJECT-TYPE
    SYNTAX Integer32
    UNITS "degrees Celsius x10"
    MAX-ACCESS read-only
    STATUS current
    DESCRIPTION
        "Temperature 1, signed value in tenths of a degree Celsius. Station 30."
    ::= { sentiaMANStationTemp1Values 130 }

sentiaMANStationTemp131 OBJECT-TYPE
    SYNTAX Integer32
    UNITS "degrees Celsius x10"
    MAX-ACCESS read-only
    STATUS current
    DESCRIPTION
        "Temperature 1, signed value in tenths of a degree Celsius. Station 31."
    ::= { sentiaMANStationTemp1Values 131 }

sentiaMANStationTemp132 OBJECT-TYPE
    SYNTAX Integer32
    UNITS "degrees Celsius x10"
    MAX-ACCESS read-only
    STATUS current
    DESCRIPTION
        "Temperature 1, signed value in tenths of a degree Celsius. Station 32."
    ::= { sentiaMANStationTemp1Values 132 }

sentiaMANStationTemp2Values OBJECT-IDENTITY
    STATUS current
    DESCRIPTION
        "sentiaMAN subordinate station Temp2 values. Station 01 uses
         subidentifier 101 and station 32 uses subidentifier 132."
    ::= { strataonSentiaMAN 7 }

sentiaMANStationTemp201 OBJECT-TYPE
    SYNTAX Integer32
    UNITS "degrees Celsius x10"
    MAX-ACCESS read-only
    STATUS current
    DESCRIPTION
        "Temperature 2, signed value in tenths of a degree Celsius. Station 01."
    ::= { sentiaMANStationTemp2Values 101 }

sentiaMANStationTemp202 OBJECT-TYPE
    SYNTAX Integer32
    UNITS "degrees Celsius x10"
    MAX-ACCESS read-only
    STATUS current
    DESCRIPTION
        "Temperature 2, signed value in tenths of a degree Celsius. Station 02."
    ::= { sentiaMANStationTemp2Values 102 }

sentiaMANStationTemp203 OBJECT-TYPE
    SYNTAX Integer32
    UNITS "degrees Celsius x10"
    MAX-ACCESS read-only
    STATUS current
    DESCRIPTION
        "Temperature 2, signed value in tenths of a degree Celsius. Station 03."
    ::= { sentiaMANStationTemp2Values 103 }

sentiaMANStationTemp204 OBJECT-TYPE
    SYNTAX Integer32
    UNITS "degrees Celsius x10"
    MAX-ACCESS read-only
    STATUS current
    DESCRIPTION
        "Temperature 2, signed value in tenths of a degree Celsius. Station 04."
    ::= { sentiaMANStationTemp2Values 104 }

sentiaMANStationTemp205 OBJECT-TYPE
    SYNTAX Integer32
    UNITS "degrees Celsius x10"
    MAX-ACCESS read-only
    STATUS current
    DESCRIPTION
        "Temperature 2, signed value in tenths of a degree Celsius. Station 05."
    ::= { sentiaMANStationTemp2Values 105 }

sentiaMANStationTemp206 OBJECT-TYPE
    SYNTAX Integer32
    UNITS "degrees Celsius x10"
    MAX-ACCESS read-only
    STATUS current
    DESCRIPTION
        "Temperature 2, signed value in tenths of a degree Celsius. Station 06."
    ::= { sentiaMANStationTemp2Values 106 }

sentiaMANStationTemp207 OBJECT-TYPE
    SYNTAX Integer32
    UNITS "degrees Celsius x10"
    MAX-ACCESS read-only
    STATUS current
    DESCRIPTION
        "Temperature 2, signed value in tenths of a degree Celsius. Station 07."
    ::= { sentiaMANStationTemp2Values 107 }

sentiaMANStationTemp208 OBJECT-TYPE
    SYNTAX Integer32
    UNITS "degrees Celsius x10"
    MAX-ACCESS read-only
    STATUS current
    DESCRIPTION
        "Temperature 2, signed value in tenths of a degree Celsius. Station 08."
    ::= { sentiaMANStationTemp2Values 108 }

sentiaMANStationTemp209 OBJECT-TYPE
    SYNTAX Integer32
    UNITS "degrees Celsius x10"
    MAX-ACCESS read-only
    STATUS current
    DESCRIPTION
        "Temperature 2, signed value in tenths of a degree Celsius. Station 09."
    ::= { sentiaMANStationTemp2Values 109 }

sentiaMANStationTemp210 OBJECT-TYPE
    SYNTAX Integer32
    UNITS "degrees Celsius x10"
    MAX-ACCESS read-only
    STATUS current
    DESCRIPTION
        "Temperature 2, signed value in tenths of a degree Celsius. Station 10."
    ::= { sentiaMANStationTemp2Values 110 }

sentiaMANStationTemp211 OBJECT-TYPE
    SYNTAX Integer32
    UNITS "degrees Celsius x10"
    MAX-ACCESS read-only
    STATUS current
    DESCRIPTION
        "Temperature 2, signed value in tenths of a degree Celsius. Station 11."
    ::= { sentiaMANStationTemp2Values 111 }

sentiaMANStationTemp212 OBJECT-TYPE
    SYNTAX Integer32
    UNITS "degrees Celsius x10"
    MAX-ACCESS read-only
    STATUS current
    DESCRIPTION
        "Temperature 2, signed value in tenths of a degree Celsius. Station 12."
    ::= { sentiaMANStationTemp2Values 112 }

sentiaMANStationTemp213 OBJECT-TYPE
    SYNTAX Integer32
    UNITS "degrees Celsius x10"
    MAX-ACCESS read-only
    STATUS current
    DESCRIPTION
        "Temperature 2, signed value in tenths of a degree Celsius. Station 13."
    ::= { sentiaMANStationTemp2Values 113 }

sentiaMANStationTemp214 OBJECT-TYPE
    SYNTAX Integer32
    UNITS "degrees Celsius x10"
    MAX-ACCESS read-only
    STATUS current
    DESCRIPTION
        "Temperature 2, signed value in tenths of a degree Celsius. Station 14."
    ::= { sentiaMANStationTemp2Values 114 }

sentiaMANStationTemp215 OBJECT-TYPE
    SYNTAX Integer32
    UNITS "degrees Celsius x10"
    MAX-ACCESS read-only
    STATUS current
    DESCRIPTION
        "Temperature 2, signed value in tenths of a degree Celsius. Station 15."
    ::= { sentiaMANStationTemp2Values 115 }

sentiaMANStationTemp216 OBJECT-TYPE
    SYNTAX Integer32
    UNITS "degrees Celsius x10"
    MAX-ACCESS read-only
    STATUS current
    DESCRIPTION
        "Temperature 2, signed value in tenths of a degree Celsius. Station 16."
    ::= { sentiaMANStationTemp2Values 116 }

sentiaMANStationTemp217 OBJECT-TYPE
    SYNTAX Integer32
    UNITS "degrees Celsius x10"
    MAX-ACCESS read-only
    STATUS current
    DESCRIPTION
        "Temperature 2, signed value in tenths of a degree Celsius. Station 17."
    ::= { sentiaMANStationTemp2Values 117 }

sentiaMANStationTemp218 OBJECT-TYPE
    SYNTAX Integer32
    UNITS "degrees Celsius x10"
    MAX-ACCESS read-only
    STATUS current
    DESCRIPTION
        "Temperature 2, signed value in tenths of a degree Celsius. Station 18."
    ::= { sentiaMANStationTemp2Values 118 }

sentiaMANStationTemp219 OBJECT-TYPE
    SYNTAX Integer32
    UNITS "degrees Celsius x10"
    MAX-ACCESS read-only
    STATUS current
    DESCRIPTION
        "Temperature 2, signed value in tenths of a degree Celsius. Station 19."
    ::= { sentiaMANStationTemp2Values 119 }

sentiaMANStationTemp220 OBJECT-TYPE
    SYNTAX Integer32
    UNITS "degrees Celsius x10"
    MAX-ACCESS read-only
    STATUS current
    DESCRIPTION
        "Temperature 2, signed value in tenths of a degree Celsius. Station 20."
    ::= { sentiaMANStationTemp2Values 120 }

sentiaMANStationTemp221 OBJECT-TYPE
    SYNTAX Integer32
    UNITS "degrees Celsius x10"
    MAX-ACCESS read-only
    STATUS current
    DESCRIPTION
        "Temperature 2, signed value in tenths of a degree Celsius. Station 21."
    ::= { sentiaMANStationTemp2Values 121 }

sentiaMANStationTemp222 OBJECT-TYPE
    SYNTAX Integer32
    UNITS "degrees Celsius x10"
    MAX-ACCESS read-only
    STATUS current
    DESCRIPTION
        "Temperature 2, signed value in tenths of a degree Celsius. Station 22."
    ::= { sentiaMANStationTemp2Values 122 }

sentiaMANStationTemp223 OBJECT-TYPE
    SYNTAX Integer32
    UNITS "degrees Celsius x10"
    MAX-ACCESS read-only
    STATUS current
    DESCRIPTION
        "Temperature 2, signed value in tenths of a degree Celsius. Station 23."
    ::= { sentiaMANStationTemp2Values 123 }

sentiaMANStationTemp224 OBJECT-TYPE
    SYNTAX Integer32
    UNITS "degrees Celsius x10"
    MAX-ACCESS read-only
    STATUS current
    DESCRIPTION
        "Temperature 2, signed value in tenths of a degree Celsius. Station 24."
    ::= { sentiaMANStationTemp2Values 124 }

sentiaMANStationTemp225 OBJECT-TYPE
    SYNTAX Integer32
    UNITS "degrees Celsius x10"
    MAX-ACCESS read-only
    STATUS current
    DESCRIPTION
        "Temperature 2, signed value in tenths of a degree Celsius. Station 25."
    ::= { sentiaMANStationTemp2Values 125 }

sentiaMANStationTemp226 OBJECT-TYPE
    SYNTAX Integer32
    UNITS "degrees Celsius x10"
    MAX-ACCESS read-only
    STATUS current
    DESCRIPTION
        "Temperature 2, signed value in tenths of a degree Celsius. Station 26."
    ::= { sentiaMANStationTemp2Values 126 }

sentiaMANStationTemp227 OBJECT-TYPE
    SYNTAX Integer32
    UNITS "degrees Celsius x10"
    MAX-ACCESS read-only
    STATUS current
    DESCRIPTION
        "Temperature 2, signed value in tenths of a degree Celsius. Station 27."
    ::= { sentiaMANStationTemp2Values 127 }

sentiaMANStationTemp228 OBJECT-TYPE
    SYNTAX Integer32
    UNITS "degrees Celsius x10"
    MAX-ACCESS read-only
    STATUS current
    DESCRIPTION
        "Temperature 2, signed value in tenths of a degree Celsius. Station 28."
    ::= { sentiaMANStationTemp2Values 128 }

sentiaMANStationTemp229 OBJECT-TYPE
    SYNTAX Integer32
    UNITS "degrees Celsius x10"
    MAX-ACCESS read-only
    STATUS current
    DESCRIPTION
        "Temperature 2, signed value in tenths of a degree Celsius. Station 29."
    ::= { sentiaMANStationTemp2Values 129 }

sentiaMANStationTemp230 OBJECT-TYPE
    SYNTAX Integer32
    UNITS "degrees Celsius x10"
    MAX-ACCESS read-only
    STATUS current
    DESCRIPTION
        "Temperature 2, signed value in tenths of a degree Celsius. Station 30."
    ::= { sentiaMANStationTemp2Values 130 }

sentiaMANStationTemp231 OBJECT-TYPE
    SYNTAX Integer32
    UNITS "degrees Celsius x10"
    MAX-ACCESS read-only
    STATUS current
    DESCRIPTION
        "Temperature 2, signed value in tenths of a degree Celsius. Station 31."
    ::= { sentiaMANStationTemp2Values 131 }

sentiaMANStationTemp232 OBJECT-TYPE
    SYNTAX Integer32
    UNITS "degrees Celsius x10"
    MAX-ACCESS read-only
    STATUS current
    DESCRIPTION
        "Temperature 2, signed value in tenths of a degree Celsius. Station 32."
    ::= { sentiaMANStationTemp2Values 132 }

sentiaMANStationTemp3Values OBJECT-IDENTITY
    STATUS current
    DESCRIPTION
        "sentiaMAN subordinate station Temp3 values. Station 01 uses
         subidentifier 101 and station 32 uses subidentifier 132."
    ::= { strataonSentiaMAN 8 }

sentiaMANStationTemp301 OBJECT-TYPE
    SYNTAX Integer32
    UNITS "degrees Celsius x10"
    MAX-ACCESS read-only
    STATUS current
    DESCRIPTION
        "Temperature 3, signed value in tenths of a degree Celsius. Station 01."
    ::= { sentiaMANStationTemp3Values 101 }

sentiaMANStationTemp302 OBJECT-TYPE
    SYNTAX Integer32
    UNITS "degrees Celsius x10"
    MAX-ACCESS read-only
    STATUS current
    DESCRIPTION
        "Temperature 3, signed value in tenths of a degree Celsius. Station 02."
    ::= { sentiaMANStationTemp3Values 102 }

sentiaMANStationTemp303 OBJECT-TYPE
    SYNTAX Integer32
    UNITS "degrees Celsius x10"
    MAX-ACCESS read-only
    STATUS current
    DESCRIPTION
        "Temperature 3, signed value in tenths of a degree Celsius. Station 03."
    ::= { sentiaMANStationTemp3Values 103 }

sentiaMANStationTemp304 OBJECT-TYPE
    SYNTAX Integer32
    UNITS "degrees Celsius x10"
    MAX-ACCESS read-only
    STATUS current
    DESCRIPTION
        "Temperature 3, signed value in tenths of a degree Celsius. Station 04."
    ::= { sentiaMANStationTemp3Values 104 }

sentiaMANStationTemp305 OBJECT-TYPE
    SYNTAX Integer32
    UNITS "degrees Celsius x10"
    MAX-ACCESS read-only
    STATUS current
    DESCRIPTION
        "Temperature 3, signed value in tenths of a degree Celsius. Station 05."
    ::= { sentiaMANStationTemp3Values 105 }

sentiaMANStationTemp306 OBJECT-TYPE
    SYNTAX Integer32
    UNITS "degrees Celsius x10"
    MAX-ACCESS read-only
    STATUS current
    DESCRIPTION
        "Temperature 3, signed value in tenths of a degree Celsius. Station 06."
    ::= { sentiaMANStationTemp3Values 106 }

sentiaMANStationTemp307 OBJECT-TYPE
    SYNTAX Integer32
    UNITS "degrees Celsius x10"
    MAX-ACCESS read-only
    STATUS current
    DESCRIPTION
        "Temperature 3, signed value in tenths of a degree Celsius. Station 07."
    ::= { sentiaMANStationTemp3Values 107 }

sentiaMANStationTemp308 OBJECT-TYPE
    SYNTAX Integer32
    UNITS "degrees Celsius x10"
    MAX-ACCESS read-only
    STATUS current
    DESCRIPTION
        "Temperature 3, signed value in tenths of a degree Celsius. Station 08."
    ::= { sentiaMANStationTemp3Values 108 }

sentiaMANStationTemp309 OBJECT-TYPE
    SYNTAX Integer32
    UNITS "degrees Celsius x10"
    MAX-ACCESS read-only
    STATUS current
    DESCRIPTION
        "Temperature 3, signed value in tenths of a degree Celsius. Station 09."
    ::= { sentiaMANStationTemp3Values 109 }

sentiaMANStationTemp310 OBJECT-TYPE
    SYNTAX Integer32
    UNITS "degrees Celsius x10"
    MAX-ACCESS read-only
    STATUS current
    DESCRIPTION
        "Temperature 3, signed value in tenths of a degree Celsius. Station 10."
    ::= { sentiaMANStationTemp3Values 110 }

sentiaMANStationTemp311 OBJECT-TYPE
    SYNTAX Integer32
    UNITS "degrees Celsius x10"
    MAX-ACCESS read-only
    STATUS current
    DESCRIPTION
        "Temperature 3, signed value in tenths of a degree Celsius. Station 11."
    ::= { sentiaMANStationTemp3Values 111 }

sentiaMANStationTemp312 OBJECT-TYPE
    SYNTAX Integer32
    UNITS "degrees Celsius x10"
    MAX-ACCESS read-only
    STATUS current
    DESCRIPTION
        "Temperature 3, signed value in tenths of a degree Celsius. Station 12."
    ::= { sentiaMANStationTemp3Values 112 }

sentiaMANStationTemp313 OBJECT-TYPE
    SYNTAX Integer32
    UNITS "degrees Celsius x10"
    MAX-ACCESS read-only
    STATUS current
    DESCRIPTION
        "Temperature 3, signed value in tenths of a degree Celsius. Station 13."
    ::= { sentiaMANStationTemp3Values 113 }

sentiaMANStationTemp314 OBJECT-TYPE
    SYNTAX Integer32
    UNITS "degrees Celsius x10"
    MAX-ACCESS read-only
    STATUS current
    DESCRIPTION
        "Temperature 3, signed value in tenths of a degree Celsius. Station 14."
    ::= { sentiaMANStationTemp3Values 114 }

sentiaMANStationTemp315 OBJECT-TYPE
    SYNTAX Integer32
    UNITS "degrees Celsius x10"
    MAX-ACCESS read-only
    STATUS current
    DESCRIPTION
        "Temperature 3, signed value in tenths of a degree Celsius. Station 15."
    ::= { sentiaMANStationTemp3Values 115 }

sentiaMANStationTemp316 OBJECT-TYPE
    SYNTAX Integer32
    UNITS "degrees Celsius x10"
    MAX-ACCESS read-only
    STATUS current
    DESCRIPTION
        "Temperature 3, signed value in tenths of a degree Celsius. Station 16."
    ::= { sentiaMANStationTemp3Values 116 }

sentiaMANStationTemp317 OBJECT-TYPE
    SYNTAX Integer32
    UNITS "degrees Celsius x10"
    MAX-ACCESS read-only
    STATUS current
    DESCRIPTION
        "Temperature 3, signed value in tenths of a degree Celsius. Station 17."
    ::= { sentiaMANStationTemp3Values 117 }

sentiaMANStationTemp318 OBJECT-TYPE
    SYNTAX Integer32
    UNITS "degrees Celsius x10"
    MAX-ACCESS read-only
    STATUS current
    DESCRIPTION
        "Temperature 3, signed value in tenths of a degree Celsius. Station 18."
    ::= { sentiaMANStationTemp3Values 118 }

sentiaMANStationTemp319 OBJECT-TYPE
    SYNTAX Integer32
    UNITS "degrees Celsius x10"
    MAX-ACCESS read-only
    STATUS current
    DESCRIPTION
        "Temperature 3, signed value in tenths of a degree Celsius. Station 19."
    ::= { sentiaMANStationTemp3Values 119 }

sentiaMANStationTemp320 OBJECT-TYPE
    SYNTAX Integer32
    UNITS "degrees Celsius x10"
    MAX-ACCESS read-only
    STATUS current
    DESCRIPTION
        "Temperature 3, signed value in tenths of a degree Celsius. Station 20."
    ::= { sentiaMANStationTemp3Values 120 }

sentiaMANStationTemp321 OBJECT-TYPE
    SYNTAX Integer32
    UNITS "degrees Celsius x10"
    MAX-ACCESS read-only
    STATUS current
    DESCRIPTION
        "Temperature 3, signed value in tenths of a degree Celsius. Station 21."
    ::= { sentiaMANStationTemp3Values 121 }

sentiaMANStationTemp322 OBJECT-TYPE
    SYNTAX Integer32
    UNITS "degrees Celsius x10"
    MAX-ACCESS read-only
    STATUS current
    DESCRIPTION
        "Temperature 3, signed value in tenths of a degree Celsius. Station 22."
    ::= { sentiaMANStationTemp3Values 122 }

sentiaMANStationTemp323 OBJECT-TYPE
    SYNTAX Integer32
    UNITS "degrees Celsius x10"
    MAX-ACCESS read-only
    STATUS current
    DESCRIPTION
        "Temperature 3, signed value in tenths of a degree Celsius. Station 23."
    ::= { sentiaMANStationTemp3Values 123 }

sentiaMANStationTemp324 OBJECT-TYPE
    SYNTAX Integer32
    UNITS "degrees Celsius x10"
    MAX-ACCESS read-only
    STATUS current
    DESCRIPTION
        "Temperature 3, signed value in tenths of a degree Celsius. Station 24."
    ::= { sentiaMANStationTemp3Values 124 }

sentiaMANStationTemp325 OBJECT-TYPE
    SYNTAX Integer32
    UNITS "degrees Celsius x10"
    MAX-ACCESS read-only
    STATUS current
    DESCRIPTION
        "Temperature 3, signed value in tenths of a degree Celsius. Station 25."
    ::= { sentiaMANStationTemp3Values 125 }

sentiaMANStationTemp326 OBJECT-TYPE
    SYNTAX Integer32
    UNITS "degrees Celsius x10"
    MAX-ACCESS read-only
    STATUS current
    DESCRIPTION
        "Temperature 3, signed value in tenths of a degree Celsius. Station 26."
    ::= { sentiaMANStationTemp3Values 126 }

sentiaMANStationTemp327 OBJECT-TYPE
    SYNTAX Integer32
    UNITS "degrees Celsius x10"
    MAX-ACCESS read-only
    STATUS current
    DESCRIPTION
        "Temperature 3, signed value in tenths of a degree Celsius. Station 27."
    ::= { sentiaMANStationTemp3Values 127 }

sentiaMANStationTemp328 OBJECT-TYPE
    SYNTAX Integer32
    UNITS "degrees Celsius x10"
    MAX-ACCESS read-only
    STATUS current
    DESCRIPTION
        "Temperature 3, signed value in tenths of a degree Celsius. Station 28."
    ::= { sentiaMANStationTemp3Values 128 }

sentiaMANStationTemp329 OBJECT-TYPE
    SYNTAX Integer32
    UNITS "degrees Celsius x10"
    MAX-ACCESS read-only
    STATUS current
    DESCRIPTION
        "Temperature 3, signed value in tenths of a degree Celsius. Station 29."
    ::= { sentiaMANStationTemp3Values 129 }

sentiaMANStationTemp330 OBJECT-TYPE
    SYNTAX Integer32
    UNITS "degrees Celsius x10"
    MAX-ACCESS read-only
    STATUS current
    DESCRIPTION
        "Temperature 3, signed value in tenths of a degree Celsius. Station 30."
    ::= { sentiaMANStationTemp3Values 130 }

sentiaMANStationTemp331 OBJECT-TYPE
    SYNTAX Integer32
    UNITS "degrees Celsius x10"
    MAX-ACCESS read-only
    STATUS current
    DESCRIPTION
        "Temperature 3, signed value in tenths of a degree Celsius. Station 31."
    ::= { sentiaMANStationTemp3Values 131 }

sentiaMANStationTemp332 OBJECT-TYPE
    SYNTAX Integer32
    UNITS "degrees Celsius x10"
    MAX-ACCESS read-only
    STATUS current
    DESCRIPTION
        "Temperature 3, signed value in tenths of a degree Celsius. Station 32."
    ::= { sentiaMANStationTemp3Values 132 }

sentiaMANStationHumidityValues OBJECT-IDENTITY
    STATUS current
    DESCRIPTION
        "sentiaMAN subordinate station Humidity values. Station 01 uses
         subidentifier 101 and station 32 uses subidentifier 132."
    ::= { strataonSentiaMAN 9 }

sentiaMANStationHumidity01 OBJECT-TYPE
    SYNTAX Gauge32
    UNITS "percent RH x10"
    MAX-ACCESS read-only
    STATUS current
    DESCRIPTION
        "Relative humidity, value in tenths of percent. Station 01."
    ::= { sentiaMANStationHumidityValues 101 }

sentiaMANStationHumidity02 OBJECT-TYPE
    SYNTAX Gauge32
    UNITS "percent RH x10"
    MAX-ACCESS read-only
    STATUS current
    DESCRIPTION
        "Relative humidity, value in tenths of percent. Station 02."
    ::= { sentiaMANStationHumidityValues 102 }

sentiaMANStationHumidity03 OBJECT-TYPE
    SYNTAX Gauge32
    UNITS "percent RH x10"
    MAX-ACCESS read-only
    STATUS current
    DESCRIPTION
        "Relative humidity, value in tenths of percent. Station 03."
    ::= { sentiaMANStationHumidityValues 103 }

sentiaMANStationHumidity04 OBJECT-TYPE
    SYNTAX Gauge32
    UNITS "percent RH x10"
    MAX-ACCESS read-only
    STATUS current
    DESCRIPTION
        "Relative humidity, value in tenths of percent. Station 04."
    ::= { sentiaMANStationHumidityValues 104 }

sentiaMANStationHumidity05 OBJECT-TYPE
    SYNTAX Gauge32
    UNITS "percent RH x10"
    MAX-ACCESS read-only
    STATUS current
    DESCRIPTION
        "Relative humidity, value in tenths of percent. Station 05."
    ::= { sentiaMANStationHumidityValues 105 }

sentiaMANStationHumidity06 OBJECT-TYPE
    SYNTAX Gauge32
    UNITS "percent RH x10"
    MAX-ACCESS read-only
    STATUS current
    DESCRIPTION
        "Relative humidity, value in tenths of percent. Station 06."
    ::= { sentiaMANStationHumidityValues 106 }

sentiaMANStationHumidity07 OBJECT-TYPE
    SYNTAX Gauge32
    UNITS "percent RH x10"
    MAX-ACCESS read-only
    STATUS current
    DESCRIPTION
        "Relative humidity, value in tenths of percent. Station 07."
    ::= { sentiaMANStationHumidityValues 107 }

sentiaMANStationHumidity08 OBJECT-TYPE
    SYNTAX Gauge32
    UNITS "percent RH x10"
    MAX-ACCESS read-only
    STATUS current
    DESCRIPTION
        "Relative humidity, value in tenths of percent. Station 08."
    ::= { sentiaMANStationHumidityValues 108 }

sentiaMANStationHumidity09 OBJECT-TYPE
    SYNTAX Gauge32
    UNITS "percent RH x10"
    MAX-ACCESS read-only
    STATUS current
    DESCRIPTION
        "Relative humidity, value in tenths of percent. Station 09."
    ::= { sentiaMANStationHumidityValues 109 }

sentiaMANStationHumidity10 OBJECT-TYPE
    SYNTAX Gauge32
    UNITS "percent RH x10"
    MAX-ACCESS read-only
    STATUS current
    DESCRIPTION
        "Relative humidity, value in tenths of percent. Station 10."
    ::= { sentiaMANStationHumidityValues 110 }

sentiaMANStationHumidity11 OBJECT-TYPE
    SYNTAX Gauge32
    UNITS "percent RH x10"
    MAX-ACCESS read-only
    STATUS current
    DESCRIPTION
        "Relative humidity, value in tenths of percent. Station 11."
    ::= { sentiaMANStationHumidityValues 111 }

sentiaMANStationHumidity12 OBJECT-TYPE
    SYNTAX Gauge32
    UNITS "percent RH x10"
    MAX-ACCESS read-only
    STATUS current
    DESCRIPTION
        "Relative humidity, value in tenths of percent. Station 12."
    ::= { sentiaMANStationHumidityValues 112 }

sentiaMANStationHumidity13 OBJECT-TYPE
    SYNTAX Gauge32
    UNITS "percent RH x10"
    MAX-ACCESS read-only
    STATUS current
    DESCRIPTION
        "Relative humidity, value in tenths of percent. Station 13."
    ::= { sentiaMANStationHumidityValues 113 }

sentiaMANStationHumidity14 OBJECT-TYPE
    SYNTAX Gauge32
    UNITS "percent RH x10"
    MAX-ACCESS read-only
    STATUS current
    DESCRIPTION
        "Relative humidity, value in tenths of percent. Station 14."
    ::= { sentiaMANStationHumidityValues 114 }

sentiaMANStationHumidity15 OBJECT-TYPE
    SYNTAX Gauge32
    UNITS "percent RH x10"
    MAX-ACCESS read-only
    STATUS current
    DESCRIPTION
        "Relative humidity, value in tenths of percent. Station 15."
    ::= { sentiaMANStationHumidityValues 115 }

sentiaMANStationHumidity16 OBJECT-TYPE
    SYNTAX Gauge32
    UNITS "percent RH x10"
    MAX-ACCESS read-only
    STATUS current
    DESCRIPTION
        "Relative humidity, value in tenths of percent. Station 16."
    ::= { sentiaMANStationHumidityValues 116 }

sentiaMANStationHumidity17 OBJECT-TYPE
    SYNTAX Gauge32
    UNITS "percent RH x10"
    MAX-ACCESS read-only
    STATUS current
    DESCRIPTION
        "Relative humidity, value in tenths of percent. Station 17."
    ::= { sentiaMANStationHumidityValues 117 }

sentiaMANStationHumidity18 OBJECT-TYPE
    SYNTAX Gauge32
    UNITS "percent RH x10"
    MAX-ACCESS read-only
    STATUS current
    DESCRIPTION
        "Relative humidity, value in tenths of percent. Station 18."
    ::= { sentiaMANStationHumidityValues 118 }

sentiaMANStationHumidity19 OBJECT-TYPE
    SYNTAX Gauge32
    UNITS "percent RH x10"
    MAX-ACCESS read-only
    STATUS current
    DESCRIPTION
        "Relative humidity, value in tenths of percent. Station 19."
    ::= { sentiaMANStationHumidityValues 119 }

sentiaMANStationHumidity20 OBJECT-TYPE
    SYNTAX Gauge32
    UNITS "percent RH x10"
    MAX-ACCESS read-only
    STATUS current
    DESCRIPTION
        "Relative humidity, value in tenths of percent. Station 20."
    ::= { sentiaMANStationHumidityValues 120 }

sentiaMANStationHumidity21 OBJECT-TYPE
    SYNTAX Gauge32
    UNITS "percent RH x10"
    MAX-ACCESS read-only
    STATUS current
    DESCRIPTION
        "Relative humidity, value in tenths of percent. Station 21."
    ::= { sentiaMANStationHumidityValues 121 }

sentiaMANStationHumidity22 OBJECT-TYPE
    SYNTAX Gauge32
    UNITS "percent RH x10"
    MAX-ACCESS read-only
    STATUS current
    DESCRIPTION
        "Relative humidity, value in tenths of percent. Station 22."
    ::= { sentiaMANStationHumidityValues 122 }

sentiaMANStationHumidity23 OBJECT-TYPE
    SYNTAX Gauge32
    UNITS "percent RH x10"
    MAX-ACCESS read-only
    STATUS current
    DESCRIPTION
        "Relative humidity, value in tenths of percent. Station 23."
    ::= { sentiaMANStationHumidityValues 123 }

sentiaMANStationHumidity24 OBJECT-TYPE
    SYNTAX Gauge32
    UNITS "percent RH x10"
    MAX-ACCESS read-only
    STATUS current
    DESCRIPTION
        "Relative humidity, value in tenths of percent. Station 24."
    ::= { sentiaMANStationHumidityValues 124 }

sentiaMANStationHumidity25 OBJECT-TYPE
    SYNTAX Gauge32
    UNITS "percent RH x10"
    MAX-ACCESS read-only
    STATUS current
    DESCRIPTION
        "Relative humidity, value in tenths of percent. Station 25."
    ::= { sentiaMANStationHumidityValues 125 }

sentiaMANStationHumidity26 OBJECT-TYPE
    SYNTAX Gauge32
    UNITS "percent RH x10"
    MAX-ACCESS read-only
    STATUS current
    DESCRIPTION
        "Relative humidity, value in tenths of percent. Station 26."
    ::= { sentiaMANStationHumidityValues 126 }

sentiaMANStationHumidity27 OBJECT-TYPE
    SYNTAX Gauge32
    UNITS "percent RH x10"
    MAX-ACCESS read-only
    STATUS current
    DESCRIPTION
        "Relative humidity, value in tenths of percent. Station 27."
    ::= { sentiaMANStationHumidityValues 127 }

sentiaMANStationHumidity28 OBJECT-TYPE
    SYNTAX Gauge32
    UNITS "percent RH x10"
    MAX-ACCESS read-only
    STATUS current
    DESCRIPTION
        "Relative humidity, value in tenths of percent. Station 28."
    ::= { sentiaMANStationHumidityValues 128 }

sentiaMANStationHumidity29 OBJECT-TYPE
    SYNTAX Gauge32
    UNITS "percent RH x10"
    MAX-ACCESS read-only
    STATUS current
    DESCRIPTION
        "Relative humidity, value in tenths of percent. Station 29."
    ::= { sentiaMANStationHumidityValues 129 }

sentiaMANStationHumidity30 OBJECT-TYPE
    SYNTAX Gauge32
    UNITS "percent RH x10"
    MAX-ACCESS read-only
    STATUS current
    DESCRIPTION
        "Relative humidity, value in tenths of percent. Station 30."
    ::= { sentiaMANStationHumidityValues 130 }

sentiaMANStationHumidity31 OBJECT-TYPE
    SYNTAX Gauge32
    UNITS "percent RH x10"
    MAX-ACCESS read-only
    STATUS current
    DESCRIPTION
        "Relative humidity, value in tenths of percent. Station 31."
    ::= { sentiaMANStationHumidityValues 131 }

sentiaMANStationHumidity32 OBJECT-TYPE
    SYNTAX Gauge32
    UNITS "percent RH x10"
    MAX-ACCESS read-only
    STATUS current
    DESCRIPTION
        "Relative humidity, value in tenths of percent. Station 32."
    ::= { sentiaMANStationHumidityValues 132 }

sentiaMANStationAlarmStates OBJECT-IDENTITY
    STATUS current
    DESCRIPTION
        "sentiaMAN subordinate station AlarmState values. Station 01 uses
         subidentifier 101 and station 32 uses subidentifier 132."
    ::= { strataonSentiaMAN 10 }

sentiaMANStationAlarmState01 OBJECT-TYPE
    SYNTAX Integer32 (0..1)
    MAX-ACCESS read-only
    STATUS current
    DESCRIPTION
        "Alarm state: 0 = normal, 1 = alarm. Station 01."
    ::= { sentiaMANStationAlarmStates 101 }

sentiaMANStationAlarmState02 OBJECT-TYPE
    SYNTAX Integer32 (0..1)
    MAX-ACCESS read-only
    STATUS current
    DESCRIPTION
        "Alarm state: 0 = normal, 1 = alarm. Station 02."
    ::= { sentiaMANStationAlarmStates 102 }

sentiaMANStationAlarmState03 OBJECT-TYPE
    SYNTAX Integer32 (0..1)
    MAX-ACCESS read-only
    STATUS current
    DESCRIPTION
        "Alarm state: 0 = normal, 1 = alarm. Station 03."
    ::= { sentiaMANStationAlarmStates 103 }

sentiaMANStationAlarmState04 OBJECT-TYPE
    SYNTAX Integer32 (0..1)
    MAX-ACCESS read-only
    STATUS current
    DESCRIPTION
        "Alarm state: 0 = normal, 1 = alarm. Station 04."
    ::= { sentiaMANStationAlarmStates 104 }

sentiaMANStationAlarmState05 OBJECT-TYPE
    SYNTAX Integer32 (0..1)
    MAX-ACCESS read-only
    STATUS current
    DESCRIPTION
        "Alarm state: 0 = normal, 1 = alarm. Station 05."
    ::= { sentiaMANStationAlarmStates 105 }

sentiaMANStationAlarmState06 OBJECT-TYPE
    SYNTAX Integer32 (0..1)
    MAX-ACCESS read-only
    STATUS current
    DESCRIPTION
        "Alarm state: 0 = normal, 1 = alarm. Station 06."
    ::= { sentiaMANStationAlarmStates 106 }

sentiaMANStationAlarmState07 OBJECT-TYPE
    SYNTAX Integer32 (0..1)
    MAX-ACCESS read-only
    STATUS current
    DESCRIPTION
        "Alarm state: 0 = normal, 1 = alarm. Station 07."
    ::= { sentiaMANStationAlarmStates 107 }

sentiaMANStationAlarmState08 OBJECT-TYPE
    SYNTAX Integer32 (0..1)
    MAX-ACCESS read-only
    STATUS current
    DESCRIPTION
        "Alarm state: 0 = normal, 1 = alarm. Station 08."
    ::= { sentiaMANStationAlarmStates 108 }

sentiaMANStationAlarmState09 OBJECT-TYPE
    SYNTAX Integer32 (0..1)
    MAX-ACCESS read-only
    STATUS current
    DESCRIPTION
        "Alarm state: 0 = normal, 1 = alarm. Station 09."
    ::= { sentiaMANStationAlarmStates 109 }

sentiaMANStationAlarmState10 OBJECT-TYPE
    SYNTAX Integer32 (0..1)
    MAX-ACCESS read-only
    STATUS current
    DESCRIPTION
        "Alarm state: 0 = normal, 1 = alarm. Station 10."
    ::= { sentiaMANStationAlarmStates 110 }

sentiaMANStationAlarmState11 OBJECT-TYPE
    SYNTAX Integer32 (0..1)
    MAX-ACCESS read-only
    STATUS current
    DESCRIPTION
        "Alarm state: 0 = normal, 1 = alarm. Station 11."
    ::= { sentiaMANStationAlarmStates 111 }

sentiaMANStationAlarmState12 OBJECT-TYPE
    SYNTAX Integer32 (0..1)
    MAX-ACCESS read-only
    STATUS current
    DESCRIPTION
        "Alarm state: 0 = normal, 1 = alarm. Station 12."
    ::= { sentiaMANStationAlarmStates 112 }

sentiaMANStationAlarmState13 OBJECT-TYPE
    SYNTAX Integer32 (0..1)
    MAX-ACCESS read-only
    STATUS current
    DESCRIPTION
        "Alarm state: 0 = normal, 1 = alarm. Station 13."
    ::= { sentiaMANStationAlarmStates 113 }

sentiaMANStationAlarmState14 OBJECT-TYPE
    SYNTAX Integer32 (0..1)
    MAX-ACCESS read-only
    STATUS current
    DESCRIPTION
        "Alarm state: 0 = normal, 1 = alarm. Station 14."
    ::= { sentiaMANStationAlarmStates 114 }

sentiaMANStationAlarmState15 OBJECT-TYPE
    SYNTAX Integer32 (0..1)
    MAX-ACCESS read-only
    STATUS current
    DESCRIPTION
        "Alarm state: 0 = normal, 1 = alarm. Station 15."
    ::= { sentiaMANStationAlarmStates 115 }

sentiaMANStationAlarmState16 OBJECT-TYPE
    SYNTAX Integer32 (0..1)
    MAX-ACCESS read-only
    STATUS current
    DESCRIPTION
        "Alarm state: 0 = normal, 1 = alarm. Station 16."
    ::= { sentiaMANStationAlarmStates 116 }

sentiaMANStationAlarmState17 OBJECT-TYPE
    SYNTAX Integer32 (0..1)
    MAX-ACCESS read-only
    STATUS current
    DESCRIPTION
        "Alarm state: 0 = normal, 1 = alarm. Station 17."
    ::= { sentiaMANStationAlarmStates 117 }

sentiaMANStationAlarmState18 OBJECT-TYPE
    SYNTAX Integer32 (0..1)
    MAX-ACCESS read-only
    STATUS current
    DESCRIPTION
        "Alarm state: 0 = normal, 1 = alarm. Station 18."
    ::= { sentiaMANStationAlarmStates 118 }

sentiaMANStationAlarmState19 OBJECT-TYPE
    SYNTAX Integer32 (0..1)
    MAX-ACCESS read-only
    STATUS current
    DESCRIPTION
        "Alarm state: 0 = normal, 1 = alarm. Station 19."
    ::= { sentiaMANStationAlarmStates 119 }

sentiaMANStationAlarmState20 OBJECT-TYPE
    SYNTAX Integer32 (0..1)
    MAX-ACCESS read-only
    STATUS current
    DESCRIPTION
        "Alarm state: 0 = normal, 1 = alarm. Station 20."
    ::= { sentiaMANStationAlarmStates 120 }

sentiaMANStationAlarmState21 OBJECT-TYPE
    SYNTAX Integer32 (0..1)
    MAX-ACCESS read-only
    STATUS current
    DESCRIPTION
        "Alarm state: 0 = normal, 1 = alarm. Station 21."
    ::= { sentiaMANStationAlarmStates 121 }

sentiaMANStationAlarmState22 OBJECT-TYPE
    SYNTAX Integer32 (0..1)
    MAX-ACCESS read-only
    STATUS current
    DESCRIPTION
        "Alarm state: 0 = normal, 1 = alarm. Station 22."
    ::= { sentiaMANStationAlarmStates 122 }

sentiaMANStationAlarmState23 OBJECT-TYPE
    SYNTAX Integer32 (0..1)
    MAX-ACCESS read-only
    STATUS current
    DESCRIPTION
        "Alarm state: 0 = normal, 1 = alarm. Station 23."
    ::= { sentiaMANStationAlarmStates 123 }

sentiaMANStationAlarmState24 OBJECT-TYPE
    SYNTAX Integer32 (0..1)
    MAX-ACCESS read-only
    STATUS current
    DESCRIPTION
        "Alarm state: 0 = normal, 1 = alarm. Station 24."
    ::= { sentiaMANStationAlarmStates 124 }

sentiaMANStationAlarmState25 OBJECT-TYPE
    SYNTAX Integer32 (0..1)
    MAX-ACCESS read-only
    STATUS current
    DESCRIPTION
        "Alarm state: 0 = normal, 1 = alarm. Station 25."
    ::= { sentiaMANStationAlarmStates 125 }

sentiaMANStationAlarmState26 OBJECT-TYPE
    SYNTAX Integer32 (0..1)
    MAX-ACCESS read-only
    STATUS current
    DESCRIPTION
        "Alarm state: 0 = normal, 1 = alarm. Station 26."
    ::= { sentiaMANStationAlarmStates 126 }

sentiaMANStationAlarmState27 OBJECT-TYPE
    SYNTAX Integer32 (0..1)
    MAX-ACCESS read-only
    STATUS current
    DESCRIPTION
        "Alarm state: 0 = normal, 1 = alarm. Station 27."
    ::= { sentiaMANStationAlarmStates 127 }

sentiaMANStationAlarmState28 OBJECT-TYPE
    SYNTAX Integer32 (0..1)
    MAX-ACCESS read-only
    STATUS current
    DESCRIPTION
        "Alarm state: 0 = normal, 1 = alarm. Station 28."
    ::= { sentiaMANStationAlarmStates 128 }

sentiaMANStationAlarmState29 OBJECT-TYPE
    SYNTAX Integer32 (0..1)
    MAX-ACCESS read-only
    STATUS current
    DESCRIPTION
        "Alarm state: 0 = normal, 1 = alarm. Station 29."
    ::= { sentiaMANStationAlarmStates 129 }

sentiaMANStationAlarmState30 OBJECT-TYPE
    SYNTAX Integer32 (0..1)
    MAX-ACCESS read-only
    STATUS current
    DESCRIPTION
        "Alarm state: 0 = normal, 1 = alarm. Station 30."
    ::= { sentiaMANStationAlarmStates 130 }

sentiaMANStationAlarmState31 OBJECT-TYPE
    SYNTAX Integer32 (0..1)
    MAX-ACCESS read-only
    STATUS current
    DESCRIPTION
        "Alarm state: 0 = normal, 1 = alarm. Station 31."
    ::= { sentiaMANStationAlarmStates 131 }

sentiaMANStationAlarmState32 OBJECT-TYPE
    SYNTAX Integer32 (0..1)
    MAX-ACCESS read-only
    STATUS current
    DESCRIPTION
        "Alarm state: 0 = normal, 1 = alarm. Station 32."
    ::= { sentiaMANStationAlarmStates 132 }

sentiaMANStationLock1States OBJECT-IDENTITY
    STATUS current
    DESCRIPTION
        "sentiaMAN subordinate station Lock1State values. Station 01 uses
         subidentifier 101 and station 32 uses subidentifier 132."
    ::= { strataonSentiaMAN 11 }

sentiaMANStationLock1State01 OBJECT-TYPE
    SYNTAX Integer32 (0..1)
    MAX-ACCESS read-only
    STATUS current
    DESCRIPTION
        "Lock 1 state: 0 = unlocked, 1 = locked. Station 01."
    ::= { sentiaMANStationLock1States 101 }

sentiaMANStationLock1State02 OBJECT-TYPE
    SYNTAX Integer32 (0..1)
    MAX-ACCESS read-only
    STATUS current
    DESCRIPTION
        "Lock 1 state: 0 = unlocked, 1 = locked. Station 02."
    ::= { sentiaMANStationLock1States 102 }

sentiaMANStationLock1State03 OBJECT-TYPE
    SYNTAX Integer32 (0..1)
    MAX-ACCESS read-only
    STATUS current
    DESCRIPTION
        "Lock 1 state: 0 = unlocked, 1 = locked. Station 03."
    ::= { sentiaMANStationLock1States 103 }

sentiaMANStationLock1State04 OBJECT-TYPE
    SYNTAX Integer32 (0..1)
    MAX-ACCESS read-only
    STATUS current
    DESCRIPTION
        "Lock 1 state: 0 = unlocked, 1 = locked. Station 04."
    ::= { sentiaMANStationLock1States 104 }

sentiaMANStationLock1State05 OBJECT-TYPE
    SYNTAX Integer32 (0..1)
    MAX-ACCESS read-only
    STATUS current
    DESCRIPTION
        "Lock 1 state: 0 = unlocked, 1 = locked. Station 05."
    ::= { sentiaMANStationLock1States 105 }

sentiaMANStationLock1State06 OBJECT-TYPE
    SYNTAX Integer32 (0..1)
    MAX-ACCESS read-only
    STATUS current
    DESCRIPTION
        "Lock 1 state: 0 = unlocked, 1 = locked. Station 06."
    ::= { sentiaMANStationLock1States 106 }

sentiaMANStationLock1State07 OBJECT-TYPE
    SYNTAX Integer32 (0..1)
    MAX-ACCESS read-only
    STATUS current
    DESCRIPTION
        "Lock 1 state: 0 = unlocked, 1 = locked. Station 07."
    ::= { sentiaMANStationLock1States 107 }

sentiaMANStationLock1State08 OBJECT-TYPE
    SYNTAX Integer32 (0..1)
    MAX-ACCESS read-only
    STATUS current
    DESCRIPTION
        "Lock 1 state: 0 = unlocked, 1 = locked. Station 08."
    ::= { sentiaMANStationLock1States 108 }

sentiaMANStationLock1State09 OBJECT-TYPE
    SYNTAX Integer32 (0..1)
    MAX-ACCESS read-only
    STATUS current
    DESCRIPTION
        "Lock 1 state: 0 = unlocked, 1 = locked. Station 09."
    ::= { sentiaMANStationLock1States 109 }

sentiaMANStationLock1State10 OBJECT-TYPE
    SYNTAX Integer32 (0..1)
    MAX-ACCESS read-only
    STATUS current
    DESCRIPTION
        "Lock 1 state: 0 = unlocked, 1 = locked. Station 10."
    ::= { sentiaMANStationLock1States 110 }

sentiaMANStationLock1State11 OBJECT-TYPE
    SYNTAX Integer32 (0..1)
    MAX-ACCESS read-only
    STATUS current
    DESCRIPTION
        "Lock 1 state: 0 = unlocked, 1 = locked. Station 11."
    ::= { sentiaMANStationLock1States 111 }

sentiaMANStationLock1State12 OBJECT-TYPE
    SYNTAX Integer32 (0..1)
    MAX-ACCESS read-only
    STATUS current
    DESCRIPTION
        "Lock 1 state: 0 = unlocked, 1 = locked. Station 12."
    ::= { sentiaMANStationLock1States 112 }

sentiaMANStationLock1State13 OBJECT-TYPE
    SYNTAX Integer32 (0..1)
    MAX-ACCESS read-only
    STATUS current
    DESCRIPTION
        "Lock 1 state: 0 = unlocked, 1 = locked. Station 13."
    ::= { sentiaMANStationLock1States 113 }

sentiaMANStationLock1State14 OBJECT-TYPE
    SYNTAX Integer32 (0..1)
    MAX-ACCESS read-only
    STATUS current
    DESCRIPTION
        "Lock 1 state: 0 = unlocked, 1 = locked. Station 14."
    ::= { sentiaMANStationLock1States 114 }

sentiaMANStationLock1State15 OBJECT-TYPE
    SYNTAX Integer32 (0..1)
    MAX-ACCESS read-only
    STATUS current
    DESCRIPTION
        "Lock 1 state: 0 = unlocked, 1 = locked. Station 15."
    ::= { sentiaMANStationLock1States 115 }

sentiaMANStationLock1State16 OBJECT-TYPE
    SYNTAX Integer32 (0..1)
    MAX-ACCESS read-only
    STATUS current
    DESCRIPTION
        "Lock 1 state: 0 = unlocked, 1 = locked. Station 16."
    ::= { sentiaMANStationLock1States 116 }

sentiaMANStationLock1State17 OBJECT-TYPE
    SYNTAX Integer32 (0..1)
    MAX-ACCESS read-only
    STATUS current
    DESCRIPTION
        "Lock 1 state: 0 = unlocked, 1 = locked. Station 17."
    ::= { sentiaMANStationLock1States 117 }

sentiaMANStationLock1State18 OBJECT-TYPE
    SYNTAX Integer32 (0..1)
    MAX-ACCESS read-only
    STATUS current
    DESCRIPTION
        "Lock 1 state: 0 = unlocked, 1 = locked. Station 18."
    ::= { sentiaMANStationLock1States 118 }

sentiaMANStationLock1State19 OBJECT-TYPE
    SYNTAX Integer32 (0..1)
    MAX-ACCESS read-only
    STATUS current
    DESCRIPTION
        "Lock 1 state: 0 = unlocked, 1 = locked. Station 19."
    ::= { sentiaMANStationLock1States 119 }

sentiaMANStationLock1State20 OBJECT-TYPE
    SYNTAX Integer32 (0..1)
    MAX-ACCESS read-only
    STATUS current
    DESCRIPTION
        "Lock 1 state: 0 = unlocked, 1 = locked. Station 20."
    ::= { sentiaMANStationLock1States 120 }

sentiaMANStationLock1State21 OBJECT-TYPE
    SYNTAX Integer32 (0..1)
    MAX-ACCESS read-only
    STATUS current
    DESCRIPTION
        "Lock 1 state: 0 = unlocked, 1 = locked. Station 21."
    ::= { sentiaMANStationLock1States 121 }

sentiaMANStationLock1State22 OBJECT-TYPE
    SYNTAX Integer32 (0..1)
    MAX-ACCESS read-only
    STATUS current
    DESCRIPTION
        "Lock 1 state: 0 = unlocked, 1 = locked. Station 22."
    ::= { sentiaMANStationLock1States 122 }

sentiaMANStationLock1State23 OBJECT-TYPE
    SYNTAX Integer32 (0..1)
    MAX-ACCESS read-only
    STATUS current
    DESCRIPTION
        "Lock 1 state: 0 = unlocked, 1 = locked. Station 23."
    ::= { sentiaMANStationLock1States 123 }

sentiaMANStationLock1State24 OBJECT-TYPE
    SYNTAX Integer32 (0..1)
    MAX-ACCESS read-only
    STATUS current
    DESCRIPTION
        "Lock 1 state: 0 = unlocked, 1 = locked. Station 24."
    ::= { sentiaMANStationLock1States 124 }

sentiaMANStationLock1State25 OBJECT-TYPE
    SYNTAX Integer32 (0..1)
    MAX-ACCESS read-only
    STATUS current
    DESCRIPTION
        "Lock 1 state: 0 = unlocked, 1 = locked. Station 25."
    ::= { sentiaMANStationLock1States 125 }

sentiaMANStationLock1State26 OBJECT-TYPE
    SYNTAX Integer32 (0..1)
    MAX-ACCESS read-only
    STATUS current
    DESCRIPTION
        "Lock 1 state: 0 = unlocked, 1 = locked. Station 26."
    ::= { sentiaMANStationLock1States 126 }

sentiaMANStationLock1State27 OBJECT-TYPE
    SYNTAX Integer32 (0..1)
    MAX-ACCESS read-only
    STATUS current
    DESCRIPTION
        "Lock 1 state: 0 = unlocked, 1 = locked. Station 27."
    ::= { sentiaMANStationLock1States 127 }

sentiaMANStationLock1State28 OBJECT-TYPE
    SYNTAX Integer32 (0..1)
    MAX-ACCESS read-only
    STATUS current
    DESCRIPTION
        "Lock 1 state: 0 = unlocked, 1 = locked. Station 28."
    ::= { sentiaMANStationLock1States 128 }

sentiaMANStationLock1State29 OBJECT-TYPE
    SYNTAX Integer32 (0..1)
    MAX-ACCESS read-only
    STATUS current
    DESCRIPTION
        "Lock 1 state: 0 = unlocked, 1 = locked. Station 29."
    ::= { sentiaMANStationLock1States 129 }

sentiaMANStationLock1State30 OBJECT-TYPE
    SYNTAX Integer32 (0..1)
    MAX-ACCESS read-only
    STATUS current
    DESCRIPTION
        "Lock 1 state: 0 = unlocked, 1 = locked. Station 30."
    ::= { sentiaMANStationLock1States 130 }

sentiaMANStationLock1State31 OBJECT-TYPE
    SYNTAX Integer32 (0..1)
    MAX-ACCESS read-only
    STATUS current
    DESCRIPTION
        "Lock 1 state: 0 = unlocked, 1 = locked. Station 31."
    ::= { sentiaMANStationLock1States 131 }

sentiaMANStationLock1State32 OBJECT-TYPE
    SYNTAX Integer32 (0..1)
    MAX-ACCESS read-only
    STATUS current
    DESCRIPTION
        "Lock 1 state: 0 = unlocked, 1 = locked. Station 32."
    ::= { sentiaMANStationLock1States 132 }

sentiaMANStationDoor1States OBJECT-IDENTITY
    STATUS current
    DESCRIPTION
        "sentiaMAN subordinate station Door1State values. Station 01 uses
         subidentifier 101 and station 32 uses subidentifier 132."
    ::= { strataonSentiaMAN 12 }

sentiaMANStationDoor1State01 OBJECT-TYPE
    SYNTAX Integer32 (0..1)
    MAX-ACCESS read-only
    STATUS current
    DESCRIPTION
        "Door 1 state: 0 = closed, 1 = opened. Station 01."
    ::= { sentiaMANStationDoor1States 101 }

sentiaMANStationDoor1State02 OBJECT-TYPE
    SYNTAX Integer32 (0..1)
    MAX-ACCESS read-only
    STATUS current
    DESCRIPTION
        "Door 1 state: 0 = closed, 1 = opened. Station 02."
    ::= { sentiaMANStationDoor1States 102 }

sentiaMANStationDoor1State03 OBJECT-TYPE
    SYNTAX Integer32 (0..1)
    MAX-ACCESS read-only
    STATUS current
    DESCRIPTION
        "Door 1 state: 0 = closed, 1 = opened. Station 03."
    ::= { sentiaMANStationDoor1States 103 }

sentiaMANStationDoor1State04 OBJECT-TYPE
    SYNTAX Integer32 (0..1)
    MAX-ACCESS read-only
    STATUS current
    DESCRIPTION
        "Door 1 state: 0 = closed, 1 = opened. Station 04."
    ::= { sentiaMANStationDoor1States 104 }

sentiaMANStationDoor1State05 OBJECT-TYPE
    SYNTAX Integer32 (0..1)
    MAX-ACCESS read-only
    STATUS current
    DESCRIPTION
        "Door 1 state: 0 = closed, 1 = opened. Station 05."
    ::= { sentiaMANStationDoor1States 105 }

sentiaMANStationDoor1State06 OBJECT-TYPE
    SYNTAX Integer32 (0..1)
    MAX-ACCESS read-only
    STATUS current
    DESCRIPTION
        "Door 1 state: 0 = closed, 1 = opened. Station 06."
    ::= { sentiaMANStationDoor1States 106 }

sentiaMANStationDoor1State07 OBJECT-TYPE
    SYNTAX Integer32 (0..1)
    MAX-ACCESS read-only
    STATUS current
    DESCRIPTION
        "Door 1 state: 0 = closed, 1 = opened. Station 07."
    ::= { sentiaMANStationDoor1States 107 }

sentiaMANStationDoor1State08 OBJECT-TYPE
    SYNTAX Integer32 (0..1)
    MAX-ACCESS read-only
    STATUS current
    DESCRIPTION
        "Door 1 state: 0 = closed, 1 = opened. Station 08."
    ::= { sentiaMANStationDoor1States 108 }

sentiaMANStationDoor1State09 OBJECT-TYPE
    SYNTAX Integer32 (0..1)
    MAX-ACCESS read-only
    STATUS current
    DESCRIPTION
        "Door 1 state: 0 = closed, 1 = opened. Station 09."
    ::= { sentiaMANStationDoor1States 109 }

sentiaMANStationDoor1State10 OBJECT-TYPE
    SYNTAX Integer32 (0..1)
    MAX-ACCESS read-only
    STATUS current
    DESCRIPTION
        "Door 1 state: 0 = closed, 1 = opened. Station 10."
    ::= { sentiaMANStationDoor1States 110 }

sentiaMANStationDoor1State11 OBJECT-TYPE
    SYNTAX Integer32 (0..1)
    MAX-ACCESS read-only
    STATUS current
    DESCRIPTION
        "Door 1 state: 0 = closed, 1 = opened. Station 11."
    ::= { sentiaMANStationDoor1States 111 }

sentiaMANStationDoor1State12 OBJECT-TYPE
    SYNTAX Integer32 (0..1)
    MAX-ACCESS read-only
    STATUS current
    DESCRIPTION
        "Door 1 state: 0 = closed, 1 = opened. Station 12."
    ::= { sentiaMANStationDoor1States 112 }

sentiaMANStationDoor1State13 OBJECT-TYPE
    SYNTAX Integer32 (0..1)
    MAX-ACCESS read-only
    STATUS current
    DESCRIPTION
        "Door 1 state: 0 = closed, 1 = opened. Station 13."
    ::= { sentiaMANStationDoor1States 113 }

sentiaMANStationDoor1State14 OBJECT-TYPE
    SYNTAX Integer32 (0..1)
    MAX-ACCESS read-only
    STATUS current
    DESCRIPTION
        "Door 1 state: 0 = closed, 1 = opened. Station 14."
    ::= { sentiaMANStationDoor1States 114 }

sentiaMANStationDoor1State15 OBJECT-TYPE
    SYNTAX Integer32 (0..1)
    MAX-ACCESS read-only
    STATUS current
    DESCRIPTION
        "Door 1 state: 0 = closed, 1 = opened. Station 15."
    ::= { sentiaMANStationDoor1States 115 }

sentiaMANStationDoor1State16 OBJECT-TYPE
    SYNTAX Integer32 (0..1)
    MAX-ACCESS read-only
    STATUS current
    DESCRIPTION
        "Door 1 state: 0 = closed, 1 = opened. Station 16."
    ::= { sentiaMANStationDoor1States 116 }

sentiaMANStationDoor1State17 OBJECT-TYPE
    SYNTAX Integer32 (0..1)
    MAX-ACCESS read-only
    STATUS current
    DESCRIPTION
        "Door 1 state: 0 = closed, 1 = opened. Station 17."
    ::= { sentiaMANStationDoor1States 117 }

sentiaMANStationDoor1State18 OBJECT-TYPE
    SYNTAX Integer32 (0..1)
    MAX-ACCESS read-only
    STATUS current
    DESCRIPTION
        "Door 1 state: 0 = closed, 1 = opened. Station 18."
    ::= { sentiaMANStationDoor1States 118 }

sentiaMANStationDoor1State19 OBJECT-TYPE
    SYNTAX Integer32 (0..1)
    MAX-ACCESS read-only
    STATUS current
    DESCRIPTION
        "Door 1 state: 0 = closed, 1 = opened. Station 19."
    ::= { sentiaMANStationDoor1States 119 }

sentiaMANStationDoor1State20 OBJECT-TYPE
    SYNTAX Integer32 (0..1)
    MAX-ACCESS read-only
    STATUS current
    DESCRIPTION
        "Door 1 state: 0 = closed, 1 = opened. Station 20."
    ::= { sentiaMANStationDoor1States 120 }

sentiaMANStationDoor1State21 OBJECT-TYPE
    SYNTAX Integer32 (0..1)
    MAX-ACCESS read-only
    STATUS current
    DESCRIPTION
        "Door 1 state: 0 = closed, 1 = opened. Station 21."
    ::= { sentiaMANStationDoor1States 121 }

sentiaMANStationDoor1State22 OBJECT-TYPE
    SYNTAX Integer32 (0..1)
    MAX-ACCESS read-only
    STATUS current
    DESCRIPTION
        "Door 1 state: 0 = closed, 1 = opened. Station 22."
    ::= { sentiaMANStationDoor1States 122 }

sentiaMANStationDoor1State23 OBJECT-TYPE
    SYNTAX Integer32 (0..1)
    MAX-ACCESS read-only
    STATUS current
    DESCRIPTION
        "Door 1 state: 0 = closed, 1 = opened. Station 23."
    ::= { sentiaMANStationDoor1States 123 }

sentiaMANStationDoor1State24 OBJECT-TYPE
    SYNTAX Integer32 (0..1)
    MAX-ACCESS read-only
    STATUS current
    DESCRIPTION
        "Door 1 state: 0 = closed, 1 = opened. Station 24."
    ::= { sentiaMANStationDoor1States 124 }

sentiaMANStationDoor1State25 OBJECT-TYPE
    SYNTAX Integer32 (0..1)
    MAX-ACCESS read-only
    STATUS current
    DESCRIPTION
        "Door 1 state: 0 = closed, 1 = opened. Station 25."
    ::= { sentiaMANStationDoor1States 125 }

sentiaMANStationDoor1State26 OBJECT-TYPE
    SYNTAX Integer32 (0..1)
    MAX-ACCESS read-only
    STATUS current
    DESCRIPTION
        "Door 1 state: 0 = closed, 1 = opened. Station 26."
    ::= { sentiaMANStationDoor1States 126 }

sentiaMANStationDoor1State27 OBJECT-TYPE
    SYNTAX Integer32 (0..1)
    MAX-ACCESS read-only
    STATUS current
    DESCRIPTION
        "Door 1 state: 0 = closed, 1 = opened. Station 27."
    ::= { sentiaMANStationDoor1States 127 }

sentiaMANStationDoor1State28 OBJECT-TYPE
    SYNTAX Integer32 (0..1)
    MAX-ACCESS read-only
    STATUS current
    DESCRIPTION
        "Door 1 state: 0 = closed, 1 = opened. Station 28."
    ::= { sentiaMANStationDoor1States 128 }

sentiaMANStationDoor1State29 OBJECT-TYPE
    SYNTAX Integer32 (0..1)
    MAX-ACCESS read-only
    STATUS current
    DESCRIPTION
        "Door 1 state: 0 = closed, 1 = opened. Station 29."
    ::= { sentiaMANStationDoor1States 129 }

sentiaMANStationDoor1State30 OBJECT-TYPE
    SYNTAX Integer32 (0..1)
    MAX-ACCESS read-only
    STATUS current
    DESCRIPTION
        "Door 1 state: 0 = closed, 1 = opened. Station 30."
    ::= { sentiaMANStationDoor1States 130 }

sentiaMANStationDoor1State31 OBJECT-TYPE
    SYNTAX Integer32 (0..1)
    MAX-ACCESS read-only
    STATUS current
    DESCRIPTION
        "Door 1 state: 0 = closed, 1 = opened. Station 31."
    ::= { sentiaMANStationDoor1States 131 }

sentiaMANStationDoor1State32 OBJECT-TYPE
    SYNTAX Integer32 (0..1)
    MAX-ACCESS read-only
    STATUS current
    DESCRIPTION
        "Door 1 state: 0 = closed, 1 = opened. Station 32."
    ::= { sentiaMANStationDoor1States 132 }

sentiaMANStationLock2States OBJECT-IDENTITY
    STATUS current
    DESCRIPTION
        "sentiaMAN subordinate station Lock2State values. Station 01 uses
         subidentifier 101 and station 32 uses subidentifier 132."
    ::= { strataonSentiaMAN 13 }

sentiaMANStationLock2State01 OBJECT-TYPE
    SYNTAX Integer32 (0..1)
    MAX-ACCESS read-only
    STATUS current
    DESCRIPTION
        "Lock 2 state: 0 = unlocked, 1 = locked. Station 01."
    ::= { sentiaMANStationLock2States 101 }

sentiaMANStationLock2State02 OBJECT-TYPE
    SYNTAX Integer32 (0..1)
    MAX-ACCESS read-only
    STATUS current
    DESCRIPTION
        "Lock 2 state: 0 = unlocked, 1 = locked. Station 02."
    ::= { sentiaMANStationLock2States 102 }

sentiaMANStationLock2State03 OBJECT-TYPE
    SYNTAX Integer32 (0..1)
    MAX-ACCESS read-only
    STATUS current
    DESCRIPTION
        "Lock 2 state: 0 = unlocked, 1 = locked. Station 03."
    ::= { sentiaMANStationLock2States 103 }

sentiaMANStationLock2State04 OBJECT-TYPE
    SYNTAX Integer32 (0..1)
    MAX-ACCESS read-only
    STATUS current
    DESCRIPTION
        "Lock 2 state: 0 = unlocked, 1 = locked. Station 04."
    ::= { sentiaMANStationLock2States 104 }

sentiaMANStationLock2State05 OBJECT-TYPE
    SYNTAX Integer32 (0..1)
    MAX-ACCESS read-only
    STATUS current
    DESCRIPTION
        "Lock 2 state: 0 = unlocked, 1 = locked. Station 05."
    ::= { sentiaMANStationLock2States 105 }

sentiaMANStationLock2State06 OBJECT-TYPE
    SYNTAX Integer32 (0..1)
    MAX-ACCESS read-only
    STATUS current
    DESCRIPTION
        "Lock 2 state: 0 = unlocked, 1 = locked. Station 06."
    ::= { sentiaMANStationLock2States 106 }

sentiaMANStationLock2State07 OBJECT-TYPE
    SYNTAX Integer32 (0..1)
    MAX-ACCESS read-only
    STATUS current
    DESCRIPTION
        "Lock 2 state: 0 = unlocked, 1 = locked. Station 07."
    ::= { sentiaMANStationLock2States 107 }

sentiaMANStationLock2State08 OBJECT-TYPE
    SYNTAX Integer32 (0..1)
    MAX-ACCESS read-only
    STATUS current
    DESCRIPTION
        "Lock 2 state: 0 = unlocked, 1 = locked. Station 08."
    ::= { sentiaMANStationLock2States 108 }

sentiaMANStationLock2State09 OBJECT-TYPE
    SYNTAX Integer32 (0..1)
    MAX-ACCESS read-only
    STATUS current
    DESCRIPTION
        "Lock 2 state: 0 = unlocked, 1 = locked. Station 09."
    ::= { sentiaMANStationLock2States 109 }

sentiaMANStationLock2State10 OBJECT-TYPE
    SYNTAX Integer32 (0..1)
    MAX-ACCESS read-only
    STATUS current
    DESCRIPTION
        "Lock 2 state: 0 = unlocked, 1 = locked. Station 10."
    ::= { sentiaMANStationLock2States 110 }

sentiaMANStationLock2State11 OBJECT-TYPE
    SYNTAX Integer32 (0..1)
    MAX-ACCESS read-only
    STATUS current
    DESCRIPTION
        "Lock 2 state: 0 = unlocked, 1 = locked. Station 11."
    ::= { sentiaMANStationLock2States 111 }

sentiaMANStationLock2State12 OBJECT-TYPE
    SYNTAX Integer32 (0..1)
    MAX-ACCESS read-only
    STATUS current
    DESCRIPTION
        "Lock 2 state: 0 = unlocked, 1 = locked. Station 12."
    ::= { sentiaMANStationLock2States 112 }

sentiaMANStationLock2State13 OBJECT-TYPE
    SYNTAX Integer32 (0..1)
    MAX-ACCESS read-only
    STATUS current
    DESCRIPTION
        "Lock 2 state: 0 = unlocked, 1 = locked. Station 13."
    ::= { sentiaMANStationLock2States 113 }

sentiaMANStationLock2State14 OBJECT-TYPE
    SYNTAX Integer32 (0..1)
    MAX-ACCESS read-only
    STATUS current
    DESCRIPTION
        "Lock 2 state: 0 = unlocked, 1 = locked. Station 14."
    ::= { sentiaMANStationLock2States 114 }

sentiaMANStationLock2State15 OBJECT-TYPE
    SYNTAX Integer32 (0..1)
    MAX-ACCESS read-only
    STATUS current
    DESCRIPTION
        "Lock 2 state: 0 = unlocked, 1 = locked. Station 15."
    ::= { sentiaMANStationLock2States 115 }

sentiaMANStationLock2State16 OBJECT-TYPE
    SYNTAX Integer32 (0..1)
    MAX-ACCESS read-only
    STATUS current
    DESCRIPTION
        "Lock 2 state: 0 = unlocked, 1 = locked. Station 16."
    ::= { sentiaMANStationLock2States 116 }

sentiaMANStationLock2State17 OBJECT-TYPE
    SYNTAX Integer32 (0..1)
    MAX-ACCESS read-only
    STATUS current
    DESCRIPTION
        "Lock 2 state: 0 = unlocked, 1 = locked. Station 17."
    ::= { sentiaMANStationLock2States 117 }

sentiaMANStationLock2State18 OBJECT-TYPE
    SYNTAX Integer32 (0..1)
    MAX-ACCESS read-only
    STATUS current
    DESCRIPTION
        "Lock 2 state: 0 = unlocked, 1 = locked. Station 18."
    ::= { sentiaMANStationLock2States 118 }

sentiaMANStationLock2State19 OBJECT-TYPE
    SYNTAX Integer32 (0..1)
    MAX-ACCESS read-only
    STATUS current
    DESCRIPTION
        "Lock 2 state: 0 = unlocked, 1 = locked. Station 19."
    ::= { sentiaMANStationLock2States 119 }

sentiaMANStationLock2State20 OBJECT-TYPE
    SYNTAX Integer32 (0..1)
    MAX-ACCESS read-only
    STATUS current
    DESCRIPTION
        "Lock 2 state: 0 = unlocked, 1 = locked. Station 20."
    ::= { sentiaMANStationLock2States 120 }

sentiaMANStationLock2State21 OBJECT-TYPE
    SYNTAX Integer32 (0..1)
    MAX-ACCESS read-only
    STATUS current
    DESCRIPTION
        "Lock 2 state: 0 = unlocked, 1 = locked. Station 21."
    ::= { sentiaMANStationLock2States 121 }

sentiaMANStationLock2State22 OBJECT-TYPE
    SYNTAX Integer32 (0..1)
    MAX-ACCESS read-only
    STATUS current
    DESCRIPTION
        "Lock 2 state: 0 = unlocked, 1 = locked. Station 22."
    ::= { sentiaMANStationLock2States 122 }

sentiaMANStationLock2State23 OBJECT-TYPE
    SYNTAX Integer32 (0..1)
    MAX-ACCESS read-only
    STATUS current
    DESCRIPTION
        "Lock 2 state: 0 = unlocked, 1 = locked. Station 23."
    ::= { sentiaMANStationLock2States 123 }

sentiaMANStationLock2State24 OBJECT-TYPE
    SYNTAX Integer32 (0..1)
    MAX-ACCESS read-only
    STATUS current
    DESCRIPTION
        "Lock 2 state: 0 = unlocked, 1 = locked. Station 24."
    ::= { sentiaMANStationLock2States 124 }

sentiaMANStationLock2State25 OBJECT-TYPE
    SYNTAX Integer32 (0..1)
    MAX-ACCESS read-only
    STATUS current
    DESCRIPTION
        "Lock 2 state: 0 = unlocked, 1 = locked. Station 25."
    ::= { sentiaMANStationLock2States 125 }

sentiaMANStationLock2State26 OBJECT-TYPE
    SYNTAX Integer32 (0..1)
    MAX-ACCESS read-only
    STATUS current
    DESCRIPTION
        "Lock 2 state: 0 = unlocked, 1 = locked. Station 26."
    ::= { sentiaMANStationLock2States 126 }

sentiaMANStationLock2State27 OBJECT-TYPE
    SYNTAX Integer32 (0..1)
    MAX-ACCESS read-only
    STATUS current
    DESCRIPTION
        "Lock 2 state: 0 = unlocked, 1 = locked. Station 27."
    ::= { sentiaMANStationLock2States 127 }

sentiaMANStationLock2State28 OBJECT-TYPE
    SYNTAX Integer32 (0..1)
    MAX-ACCESS read-only
    STATUS current
    DESCRIPTION
        "Lock 2 state: 0 = unlocked, 1 = locked. Station 28."
    ::= { sentiaMANStationLock2States 128 }

sentiaMANStationLock2State29 OBJECT-TYPE
    SYNTAX Integer32 (0..1)
    MAX-ACCESS read-only
    STATUS current
    DESCRIPTION
        "Lock 2 state: 0 = unlocked, 1 = locked. Station 29."
    ::= { sentiaMANStationLock2States 129 }

sentiaMANStationLock2State30 OBJECT-TYPE
    SYNTAX Integer32 (0..1)
    MAX-ACCESS read-only
    STATUS current
    DESCRIPTION
        "Lock 2 state: 0 = unlocked, 1 = locked. Station 30."
    ::= { sentiaMANStationLock2States 130 }

sentiaMANStationLock2State31 OBJECT-TYPE
    SYNTAX Integer32 (0..1)
    MAX-ACCESS read-only
    STATUS current
    DESCRIPTION
        "Lock 2 state: 0 = unlocked, 1 = locked. Station 31."
    ::= { sentiaMANStationLock2States 131 }

sentiaMANStationLock2State32 OBJECT-TYPE
    SYNTAX Integer32 (0..1)
    MAX-ACCESS read-only
    STATUS current
    DESCRIPTION
        "Lock 2 state: 0 = unlocked, 1 = locked. Station 32."
    ::= { sentiaMANStationLock2States 132 }

sentiaMANStationDoor2States OBJECT-IDENTITY
    STATUS current
    DESCRIPTION
        "sentiaMAN subordinate station Door2State values. Station 01 uses
         subidentifier 101 and station 32 uses subidentifier 132."
    ::= { strataonSentiaMAN 14 }

sentiaMANStationDoor2State01 OBJECT-TYPE
    SYNTAX Integer32 (0..1)
    MAX-ACCESS read-only
    STATUS current
    DESCRIPTION
        "Door 2 state: 0 = closed, 1 = opened. Station 01."
    ::= { sentiaMANStationDoor2States 101 }

sentiaMANStationDoor2State02 OBJECT-TYPE
    SYNTAX Integer32 (0..1)
    MAX-ACCESS read-only
    STATUS current
    DESCRIPTION
        "Door 2 state: 0 = closed, 1 = opened. Station 02."
    ::= { sentiaMANStationDoor2States 102 }

sentiaMANStationDoor2State03 OBJECT-TYPE
    SYNTAX Integer32 (0..1)
    MAX-ACCESS read-only
    STATUS current
    DESCRIPTION
        "Door 2 state: 0 = closed, 1 = opened. Station 03."
    ::= { sentiaMANStationDoor2States 103 }

sentiaMANStationDoor2State04 OBJECT-TYPE
    SYNTAX Integer32 (0..1)
    MAX-ACCESS read-only
    STATUS current
    DESCRIPTION
        "Door 2 state: 0 = closed, 1 = opened. Station 04."
    ::= { sentiaMANStationDoor2States 104 }

sentiaMANStationDoor2State05 OBJECT-TYPE
    SYNTAX Integer32 (0..1)
    MAX-ACCESS read-only
    STATUS current
    DESCRIPTION
        "Door 2 state: 0 = closed, 1 = opened. Station 05."
    ::= { sentiaMANStationDoor2States 105 }

sentiaMANStationDoor2State06 OBJECT-TYPE
    SYNTAX Integer32 (0..1)
    MAX-ACCESS read-only
    STATUS current
    DESCRIPTION
        "Door 2 state: 0 = closed, 1 = opened. Station 06."
    ::= { sentiaMANStationDoor2States 106 }

sentiaMANStationDoor2State07 OBJECT-TYPE
    SYNTAX Integer32 (0..1)
    MAX-ACCESS read-only
    STATUS current
    DESCRIPTION
        "Door 2 state: 0 = closed, 1 = opened. Station 07."
    ::= { sentiaMANStationDoor2States 107 }

sentiaMANStationDoor2State08 OBJECT-TYPE
    SYNTAX Integer32 (0..1)
    MAX-ACCESS read-only
    STATUS current
    DESCRIPTION
        "Door 2 state: 0 = closed, 1 = opened. Station 08."
    ::= { sentiaMANStationDoor2States 108 }

sentiaMANStationDoor2State09 OBJECT-TYPE
    SYNTAX Integer32 (0..1)
    MAX-ACCESS read-only
    STATUS current
    DESCRIPTION
        "Door 2 state: 0 = closed, 1 = opened. Station 09."
    ::= { sentiaMANStationDoor2States 109 }

sentiaMANStationDoor2State10 OBJECT-TYPE
    SYNTAX Integer32 (0..1)
    MAX-ACCESS read-only
    STATUS current
    DESCRIPTION
        "Door 2 state: 0 = closed, 1 = opened. Station 10."
    ::= { sentiaMANStationDoor2States 110 }

sentiaMANStationDoor2State11 OBJECT-TYPE
    SYNTAX Integer32 (0..1)
    MAX-ACCESS read-only
    STATUS current
    DESCRIPTION
        "Door 2 state: 0 = closed, 1 = opened. Station 11."
    ::= { sentiaMANStationDoor2States 111 }

sentiaMANStationDoor2State12 OBJECT-TYPE
    SYNTAX Integer32 (0..1)
    MAX-ACCESS read-only
    STATUS current
    DESCRIPTION
        "Door 2 state: 0 = closed, 1 = opened. Station 12."
    ::= { sentiaMANStationDoor2States 112 }

sentiaMANStationDoor2State13 OBJECT-TYPE
    SYNTAX Integer32 (0..1)
    MAX-ACCESS read-only
    STATUS current
    DESCRIPTION
        "Door 2 state: 0 = closed, 1 = opened. Station 13."
    ::= { sentiaMANStationDoor2States 113 }

sentiaMANStationDoor2State14 OBJECT-TYPE
    SYNTAX Integer32 (0..1)
    MAX-ACCESS read-only
    STATUS current
    DESCRIPTION
        "Door 2 state: 0 = closed, 1 = opened. Station 14."
    ::= { sentiaMANStationDoor2States 114 }

sentiaMANStationDoor2State15 OBJECT-TYPE
    SYNTAX Integer32 (0..1)
    MAX-ACCESS read-only
    STATUS current
    DESCRIPTION
        "Door 2 state: 0 = closed, 1 = opened. Station 15."
    ::= { sentiaMANStationDoor2States 115 }

sentiaMANStationDoor2State16 OBJECT-TYPE
    SYNTAX Integer32 (0..1)
    MAX-ACCESS read-only
    STATUS current
    DESCRIPTION
        "Door 2 state: 0 = closed, 1 = opened. Station 16."
    ::= { sentiaMANStationDoor2States 116 }

sentiaMANStationDoor2State17 OBJECT-TYPE
    SYNTAX Integer32 (0..1)
    MAX-ACCESS read-only
    STATUS current
    DESCRIPTION
        "Door 2 state: 0 = closed, 1 = opened. Station 17."
    ::= { sentiaMANStationDoor2States 117 }

sentiaMANStationDoor2State18 OBJECT-TYPE
    SYNTAX Integer32 (0..1)
    MAX-ACCESS read-only
    STATUS current
    DESCRIPTION
        "Door 2 state: 0 = closed, 1 = opened. Station 18."
    ::= { sentiaMANStationDoor2States 118 }

sentiaMANStationDoor2State19 OBJECT-TYPE
    SYNTAX Integer32 (0..1)
    MAX-ACCESS read-only
    STATUS current
    DESCRIPTION
        "Door 2 state: 0 = closed, 1 = opened. Station 19."
    ::= { sentiaMANStationDoor2States 119 }

sentiaMANStationDoor2State20 OBJECT-TYPE
    SYNTAX Integer32 (0..1)
    MAX-ACCESS read-only
    STATUS current
    DESCRIPTION
        "Door 2 state: 0 = closed, 1 = opened. Station 20."
    ::= { sentiaMANStationDoor2States 120 }

sentiaMANStationDoor2State21 OBJECT-TYPE
    SYNTAX Integer32 (0..1)
    MAX-ACCESS read-only
    STATUS current
    DESCRIPTION
        "Door 2 state: 0 = closed, 1 = opened. Station 21."
    ::= { sentiaMANStationDoor2States 121 }

sentiaMANStationDoor2State22 OBJECT-TYPE
    SYNTAX Integer32 (0..1)
    MAX-ACCESS read-only
    STATUS current
    DESCRIPTION
        "Door 2 state: 0 = closed, 1 = opened. Station 22."
    ::= { sentiaMANStationDoor2States 122 }

sentiaMANStationDoor2State23 OBJECT-TYPE
    SYNTAX Integer32 (0..1)
    MAX-ACCESS read-only
    STATUS current
    DESCRIPTION
        "Door 2 state: 0 = closed, 1 = opened. Station 23."
    ::= { sentiaMANStationDoor2States 123 }

sentiaMANStationDoor2State24 OBJECT-TYPE
    SYNTAX Integer32 (0..1)
    MAX-ACCESS read-only
    STATUS current
    DESCRIPTION
        "Door 2 state: 0 = closed, 1 = opened. Station 24."
    ::= { sentiaMANStationDoor2States 124 }

sentiaMANStationDoor2State25 OBJECT-TYPE
    SYNTAX Integer32 (0..1)
    MAX-ACCESS read-only
    STATUS current
    DESCRIPTION
        "Door 2 state: 0 = closed, 1 = opened. Station 25."
    ::= { sentiaMANStationDoor2States 125 }

sentiaMANStationDoor2State26 OBJECT-TYPE
    SYNTAX Integer32 (0..1)
    MAX-ACCESS read-only
    STATUS current
    DESCRIPTION
        "Door 2 state: 0 = closed, 1 = opened. Station 26."
    ::= { sentiaMANStationDoor2States 126 }

sentiaMANStationDoor2State27 OBJECT-TYPE
    SYNTAX Integer32 (0..1)
    MAX-ACCESS read-only
    STATUS current
    DESCRIPTION
        "Door 2 state: 0 = closed, 1 = opened. Station 27."
    ::= { sentiaMANStationDoor2States 127 }

sentiaMANStationDoor2State28 OBJECT-TYPE
    SYNTAX Integer32 (0..1)
    MAX-ACCESS read-only
    STATUS current
    DESCRIPTION
        "Door 2 state: 0 = closed, 1 = opened. Station 28."
    ::= { sentiaMANStationDoor2States 128 }

sentiaMANStationDoor2State29 OBJECT-TYPE
    SYNTAX Integer32 (0..1)
    MAX-ACCESS read-only
    STATUS current
    DESCRIPTION
        "Door 2 state: 0 = closed, 1 = opened. Station 29."
    ::= { sentiaMANStationDoor2States 129 }

sentiaMANStationDoor2State30 OBJECT-TYPE
    SYNTAX Integer32 (0..1)
    MAX-ACCESS read-only
    STATUS current
    DESCRIPTION
        "Door 2 state: 0 = closed, 1 = opened. Station 30."
    ::= { sentiaMANStationDoor2States 130 }

sentiaMANStationDoor2State31 OBJECT-TYPE
    SYNTAX Integer32 (0..1)
    MAX-ACCESS read-only
    STATUS current
    DESCRIPTION
        "Door 2 state: 0 = closed, 1 = opened. Station 31."
    ::= { sentiaMANStationDoor2States 131 }

sentiaMANStationDoor2State32 OBJECT-TYPE
    SYNTAX Integer32 (0..1)
    MAX-ACCESS read-only
    STATUS current
    DESCRIPTION
        "Door 2 state: 0 = closed, 1 = opened. Station 32."
    ::= { sentiaMANStationDoor2States 132 }


-- =============================================================
-- sentiaPRO branch: 1.3.6.1.4.1.66204.10.5
-- =============================================================

sentiaPROTemp1 OBJECT-TYPE
    SYNTAX Integer32
    UNITS "degrees Celsius x10"
    MAX-ACCESS read-only
    STATUS current
    DESCRIPTION
        "sentiaPRO temperature 1, signed value in tenths of a degree Celsius."
    ::= { strataonSentiaPRO 1 }

sentiaPROTemp2 OBJECT-TYPE
    SYNTAX Integer32
    UNITS "degrees Celsius x10"
    MAX-ACCESS read-only
    STATUS current
    DESCRIPTION
        "sentiaPRO temperature 2, signed value in tenths of a degree Celsius."
    ::= { strataonSentiaPRO 2 }

sentiaPROTemp3 OBJECT-TYPE
    SYNTAX Integer32
    UNITS "degrees Celsius x10"
    MAX-ACCESS read-only
    STATUS current
    DESCRIPTION
        "sentiaPRO temperature 3, signed value in tenths of a degree Celsius."
    ::= { strataonSentiaPRO 3 }

sentiaPROHumidity OBJECT-TYPE
    SYNTAX Gauge32
    UNITS "percent RH x10"
    MAX-ACCESS read-only
    STATUS current
    DESCRIPTION
        "sentiaPRO relative humidity, value in tenths of percent."
    ::= { strataonSentiaPRO 4 }

sentiaPROAlarmState OBJECT-TYPE
    SYNTAX Integer32 (0..1)
    MAX-ACCESS read-only
    STATUS current
    DESCRIPTION
        "sentiaPRO alarm state: 0 = normal, 1 = alarm."
    ::= { strataonSentiaPRO 5 }

sentiaPROLock1State OBJECT-TYPE
    SYNTAX Integer32 (0..1)
    MAX-ACCESS read-only
    STATUS current
    DESCRIPTION
        "sentiaPRO lock 1 state: 0 = unlocked, 1 = locked."
    ::= { strataonSentiaPRO 6 }

sentiaPRODoor1State OBJECT-TYPE
    SYNTAX Integer32 (0..1)
    MAX-ACCESS read-only
    STATUS current
    DESCRIPTION
        "sentiaPRO door 1 state: 0 = closed, 1 = opened."
    ::= { strataonSentiaPRO 7 }

sentiaPROLock2State OBJECT-TYPE
    SYNTAX Integer32 (0..1)
    MAX-ACCESS read-only
    STATUS current
    DESCRIPTION
        "sentiaPRO lock 2 state: 0 = unlocked, 1 = locked."
    ::= { strataonSentiaPRO 8 }

sentiaPRODoor2State OBJECT-TYPE
    SYNTAX Integer32 (0..1)
    MAX-ACCESS read-only
    STATUS current
    DESCRIPTION
        "sentiaPRO door 2 state: 0 = closed, 1 = opened."
    ::= { strataonSentiaPRO 9 }

-- Conformance
-- =============================================================


-- =============================================================
-- sentiaLOK branch: 1.3.6.1.4.1.66204.10.6
-- =============================================================

sentiaLOKStationCount OBJECT-TYPE
    SYNTAX Integer32 (0..32)
    MAX-ACCESS read-only
    STATUS current
    DESCRIPTION "Number of subordinate station slots exposed by sentiaLOK."
    ::= { strataonSentiaLOK 1 }

sentiaLOKStationNodes OBJECT-IDENTITY
    STATUS current
    DESCRIPTION "sentiaLOK station node values for stations 01..32; subidentifiers 101..132."
    ::= { strataonSentiaLOK 2 }

sentiaLOKStationNode01 OBJECT-TYPE
    SYNTAX Integer32 (1..32)
    MAX-ACCESS read-only
    STATUS current
    DESCRIPTION "Subordinate station node number. Station 01."
    ::= { sentiaLOKStationNodes 101 }

sentiaLOKStationNode02 OBJECT-TYPE
    SYNTAX Integer32 (1..32)
    MAX-ACCESS read-only
    STATUS current
    DESCRIPTION "Subordinate station node number. Station 02."
    ::= { sentiaLOKStationNodes 102 }

sentiaLOKStationNode03 OBJECT-TYPE
    SYNTAX Integer32 (1..32)
    MAX-ACCESS read-only
    STATUS current
    DESCRIPTION "Subordinate station node number. Station 03."
    ::= { sentiaLOKStationNodes 103 }

sentiaLOKStationNode04 OBJECT-TYPE
    SYNTAX Integer32 (1..32)
    MAX-ACCESS read-only
    STATUS current
    DESCRIPTION "Subordinate station node number. Station 04."
    ::= { sentiaLOKStationNodes 104 }

sentiaLOKStationNode05 OBJECT-TYPE
    SYNTAX Integer32 (1..32)
    MAX-ACCESS read-only
    STATUS current
    DESCRIPTION "Subordinate station node number. Station 05."
    ::= { sentiaLOKStationNodes 105 }

sentiaLOKStationNode06 OBJECT-TYPE
    SYNTAX Integer32 (1..32)
    MAX-ACCESS read-only
    STATUS current
    DESCRIPTION "Subordinate station node number. Station 06."
    ::= { sentiaLOKStationNodes 106 }

sentiaLOKStationNode07 OBJECT-TYPE
    SYNTAX Integer32 (1..32)
    MAX-ACCESS read-only
    STATUS current
    DESCRIPTION "Subordinate station node number. Station 07."
    ::= { sentiaLOKStationNodes 107 }

sentiaLOKStationNode08 OBJECT-TYPE
    SYNTAX Integer32 (1..32)
    MAX-ACCESS read-only
    STATUS current
    DESCRIPTION "Subordinate station node number. Station 08."
    ::= { sentiaLOKStationNodes 108 }

sentiaLOKStationNode09 OBJECT-TYPE
    SYNTAX Integer32 (1..32)
    MAX-ACCESS read-only
    STATUS current
    DESCRIPTION "Subordinate station node number. Station 09."
    ::= { sentiaLOKStationNodes 109 }

sentiaLOKStationNode10 OBJECT-TYPE
    SYNTAX Integer32 (1..32)
    MAX-ACCESS read-only
    STATUS current
    DESCRIPTION "Subordinate station node number. Station 10."
    ::= { sentiaLOKStationNodes 110 }

sentiaLOKStationNode11 OBJECT-TYPE
    SYNTAX Integer32 (1..32)
    MAX-ACCESS read-only
    STATUS current
    DESCRIPTION "Subordinate station node number. Station 11."
    ::= { sentiaLOKStationNodes 111 }

sentiaLOKStationNode12 OBJECT-TYPE
    SYNTAX Integer32 (1..32)
    MAX-ACCESS read-only
    STATUS current
    DESCRIPTION "Subordinate station node number. Station 12."
    ::= { sentiaLOKStationNodes 112 }

sentiaLOKStationNode13 OBJECT-TYPE
    SYNTAX Integer32 (1..32)
    MAX-ACCESS read-only
    STATUS current
    DESCRIPTION "Subordinate station node number. Station 13."
    ::= { sentiaLOKStationNodes 113 }

sentiaLOKStationNode14 OBJECT-TYPE
    SYNTAX Integer32 (1..32)
    MAX-ACCESS read-only
    STATUS current
    DESCRIPTION "Subordinate station node number. Station 14."
    ::= { sentiaLOKStationNodes 114 }

sentiaLOKStationNode15 OBJECT-TYPE
    SYNTAX Integer32 (1..32)
    MAX-ACCESS read-only
    STATUS current
    DESCRIPTION "Subordinate station node number. Station 15."
    ::= { sentiaLOKStationNodes 115 }

sentiaLOKStationNode16 OBJECT-TYPE
    SYNTAX Integer32 (1..32)
    MAX-ACCESS read-only
    STATUS current
    DESCRIPTION "Subordinate station node number. Station 16."
    ::= { sentiaLOKStationNodes 116 }

sentiaLOKStationNode17 OBJECT-TYPE
    SYNTAX Integer32 (1..32)
    MAX-ACCESS read-only
    STATUS current
    DESCRIPTION "Subordinate station node number. Station 17."
    ::= { sentiaLOKStationNodes 117 }

sentiaLOKStationNode18 OBJECT-TYPE
    SYNTAX Integer32 (1..32)
    MAX-ACCESS read-only
    STATUS current
    DESCRIPTION "Subordinate station node number. Station 18."
    ::= { sentiaLOKStationNodes 118 }

sentiaLOKStationNode19 OBJECT-TYPE
    SYNTAX Integer32 (1..32)
    MAX-ACCESS read-only
    STATUS current
    DESCRIPTION "Subordinate station node number. Station 19."
    ::= { sentiaLOKStationNodes 119 }

sentiaLOKStationNode20 OBJECT-TYPE
    SYNTAX Integer32 (1..32)
    MAX-ACCESS read-only
    STATUS current
    DESCRIPTION "Subordinate station node number. Station 20."
    ::= { sentiaLOKStationNodes 120 }

sentiaLOKStationNode21 OBJECT-TYPE
    SYNTAX Integer32 (1..32)
    MAX-ACCESS read-only
    STATUS current
    DESCRIPTION "Subordinate station node number. Station 21."
    ::= { sentiaLOKStationNodes 121 }

sentiaLOKStationNode22 OBJECT-TYPE
    SYNTAX Integer32 (1..32)
    MAX-ACCESS read-only
    STATUS current
    DESCRIPTION "Subordinate station node number. Station 22."
    ::= { sentiaLOKStationNodes 122 }

sentiaLOKStationNode23 OBJECT-TYPE
    SYNTAX Integer32 (1..32)
    MAX-ACCESS read-only
    STATUS current
    DESCRIPTION "Subordinate station node number. Station 23."
    ::= { sentiaLOKStationNodes 123 }

sentiaLOKStationNode24 OBJECT-TYPE
    SYNTAX Integer32 (1..32)
    MAX-ACCESS read-only
    STATUS current
    DESCRIPTION "Subordinate station node number. Station 24."
    ::= { sentiaLOKStationNodes 124 }

sentiaLOKStationNode25 OBJECT-TYPE
    SYNTAX Integer32 (1..32)
    MAX-ACCESS read-only
    STATUS current
    DESCRIPTION "Subordinate station node number. Station 25."
    ::= { sentiaLOKStationNodes 125 }

sentiaLOKStationNode26 OBJECT-TYPE
    SYNTAX Integer32 (1..32)
    MAX-ACCESS read-only
    STATUS current
    DESCRIPTION "Subordinate station node number. Station 26."
    ::= { sentiaLOKStationNodes 126 }

sentiaLOKStationNode27 OBJECT-TYPE
    SYNTAX Integer32 (1..32)
    MAX-ACCESS read-only
    STATUS current
    DESCRIPTION "Subordinate station node number. Station 27."
    ::= { sentiaLOKStationNodes 127 }

sentiaLOKStationNode28 OBJECT-TYPE
    SYNTAX Integer32 (1..32)
    MAX-ACCESS read-only
    STATUS current
    DESCRIPTION "Subordinate station node number. Station 28."
    ::= { sentiaLOKStationNodes 128 }

sentiaLOKStationNode29 OBJECT-TYPE
    SYNTAX Integer32 (1..32)
    MAX-ACCESS read-only
    STATUS current
    DESCRIPTION "Subordinate station node number. Station 29."
    ::= { sentiaLOKStationNodes 129 }

sentiaLOKStationNode30 OBJECT-TYPE
    SYNTAX Integer32 (1..32)
    MAX-ACCESS read-only
    STATUS current
    DESCRIPTION "Subordinate station node number. Station 30."
    ::= { sentiaLOKStationNodes 130 }

sentiaLOKStationNode31 OBJECT-TYPE
    SYNTAX Integer32 (1..32)
    MAX-ACCESS read-only
    STATUS current
    DESCRIPTION "Subordinate station node number. Station 31."
    ::= { sentiaLOKStationNodes 131 }

sentiaLOKStationNode32 OBJECT-TYPE
    SYNTAX Integer32 (1..32)
    MAX-ACCESS read-only
    STATUS current
    DESCRIPTION "Subordinate station node number. Station 32."
    ::= { sentiaLOKStationNodes 132 }

sentiaLOKStationNames OBJECT-IDENTITY
    STATUS current
    DESCRIPTION "sentiaLOK station name values for stations 01..32; subidentifiers 101..132."
    ::= { strataonSentiaLOK 3 }

sentiaLOKStationName01 OBJECT-TYPE
    SYNTAX DisplayString
    MAX-ACCESS read-only
    STATUS current
    DESCRIPTION "Subordinate station name. Station 01."
    ::= { sentiaLOKStationNames 101 }

sentiaLOKStationName02 OBJECT-TYPE
    SYNTAX DisplayString
    MAX-ACCESS read-only
    STATUS current
    DESCRIPTION "Subordinate station name. Station 02."
    ::= { sentiaLOKStationNames 102 }

sentiaLOKStationName03 OBJECT-TYPE
    SYNTAX DisplayString
    MAX-ACCESS read-only
    STATUS current
    DESCRIPTION "Subordinate station name. Station 03."
    ::= { sentiaLOKStationNames 103 }

sentiaLOKStationName04 OBJECT-TYPE
    SYNTAX DisplayString
    MAX-ACCESS read-only
    STATUS current
    DESCRIPTION "Subordinate station name. Station 04."
    ::= { sentiaLOKStationNames 104 }

sentiaLOKStationName05 OBJECT-TYPE
    SYNTAX DisplayString
    MAX-ACCESS read-only
    STATUS current
    DESCRIPTION "Subordinate station name. Station 05."
    ::= { sentiaLOKStationNames 105 }

sentiaLOKStationName06 OBJECT-TYPE
    SYNTAX DisplayString
    MAX-ACCESS read-only
    STATUS current
    DESCRIPTION "Subordinate station name. Station 06."
    ::= { sentiaLOKStationNames 106 }

sentiaLOKStationName07 OBJECT-TYPE
    SYNTAX DisplayString
    MAX-ACCESS read-only
    STATUS current
    DESCRIPTION "Subordinate station name. Station 07."
    ::= { sentiaLOKStationNames 107 }

sentiaLOKStationName08 OBJECT-TYPE
    SYNTAX DisplayString
    MAX-ACCESS read-only
    STATUS current
    DESCRIPTION "Subordinate station name. Station 08."
    ::= { sentiaLOKStationNames 108 }

sentiaLOKStationName09 OBJECT-TYPE
    SYNTAX DisplayString
    MAX-ACCESS read-only
    STATUS current
    DESCRIPTION "Subordinate station name. Station 09."
    ::= { sentiaLOKStationNames 109 }

sentiaLOKStationName10 OBJECT-TYPE
    SYNTAX DisplayString
    MAX-ACCESS read-only
    STATUS current
    DESCRIPTION "Subordinate station name. Station 10."
    ::= { sentiaLOKStationNames 110 }

sentiaLOKStationName11 OBJECT-TYPE
    SYNTAX DisplayString
    MAX-ACCESS read-only
    STATUS current
    DESCRIPTION "Subordinate station name. Station 11."
    ::= { sentiaLOKStationNames 111 }

sentiaLOKStationName12 OBJECT-TYPE
    SYNTAX DisplayString
    MAX-ACCESS read-only
    STATUS current
    DESCRIPTION "Subordinate station name. Station 12."
    ::= { sentiaLOKStationNames 112 }

sentiaLOKStationName13 OBJECT-TYPE
    SYNTAX DisplayString
    MAX-ACCESS read-only
    STATUS current
    DESCRIPTION "Subordinate station name. Station 13."
    ::= { sentiaLOKStationNames 113 }

sentiaLOKStationName14 OBJECT-TYPE
    SYNTAX DisplayString
    MAX-ACCESS read-only
    STATUS current
    DESCRIPTION "Subordinate station name. Station 14."
    ::= { sentiaLOKStationNames 114 }

sentiaLOKStationName15 OBJECT-TYPE
    SYNTAX DisplayString
    MAX-ACCESS read-only
    STATUS current
    DESCRIPTION "Subordinate station name. Station 15."
    ::= { sentiaLOKStationNames 115 }

sentiaLOKStationName16 OBJECT-TYPE
    SYNTAX DisplayString
    MAX-ACCESS read-only
    STATUS current
    DESCRIPTION "Subordinate station name. Station 16."
    ::= { sentiaLOKStationNames 116 }

sentiaLOKStationName17 OBJECT-TYPE
    SYNTAX DisplayString
    MAX-ACCESS read-only
    STATUS current
    DESCRIPTION "Subordinate station name. Station 17."
    ::= { sentiaLOKStationNames 117 }

sentiaLOKStationName18 OBJECT-TYPE
    SYNTAX DisplayString
    MAX-ACCESS read-only
    STATUS current
    DESCRIPTION "Subordinate station name. Station 18."
    ::= { sentiaLOKStationNames 118 }

sentiaLOKStationName19 OBJECT-TYPE
    SYNTAX DisplayString
    MAX-ACCESS read-only
    STATUS current
    DESCRIPTION "Subordinate station name. Station 19."
    ::= { sentiaLOKStationNames 119 }

sentiaLOKStationName20 OBJECT-TYPE
    SYNTAX DisplayString
    MAX-ACCESS read-only
    STATUS current
    DESCRIPTION "Subordinate station name. Station 20."
    ::= { sentiaLOKStationNames 120 }

sentiaLOKStationName21 OBJECT-TYPE
    SYNTAX DisplayString
    MAX-ACCESS read-only
    STATUS current
    DESCRIPTION "Subordinate station name. Station 21."
    ::= { sentiaLOKStationNames 121 }

sentiaLOKStationName22 OBJECT-TYPE
    SYNTAX DisplayString
    MAX-ACCESS read-only
    STATUS current
    DESCRIPTION "Subordinate station name. Station 22."
    ::= { sentiaLOKStationNames 122 }

sentiaLOKStationName23 OBJECT-TYPE
    SYNTAX DisplayString
    MAX-ACCESS read-only
    STATUS current
    DESCRIPTION "Subordinate station name. Station 23."
    ::= { sentiaLOKStationNames 123 }

sentiaLOKStationName24 OBJECT-TYPE
    SYNTAX DisplayString
    MAX-ACCESS read-only
    STATUS current
    DESCRIPTION "Subordinate station name. Station 24."
    ::= { sentiaLOKStationNames 124 }

sentiaLOKStationName25 OBJECT-TYPE
    SYNTAX DisplayString
    MAX-ACCESS read-only
    STATUS current
    DESCRIPTION "Subordinate station name. Station 25."
    ::= { sentiaLOKStationNames 125 }

sentiaLOKStationName26 OBJECT-TYPE
    SYNTAX DisplayString
    MAX-ACCESS read-only
    STATUS current
    DESCRIPTION "Subordinate station name. Station 26."
    ::= { sentiaLOKStationNames 126 }

sentiaLOKStationName27 OBJECT-TYPE
    SYNTAX DisplayString
    MAX-ACCESS read-only
    STATUS current
    DESCRIPTION "Subordinate station name. Station 27."
    ::= { sentiaLOKStationNames 127 }

sentiaLOKStationName28 OBJECT-TYPE
    SYNTAX DisplayString
    MAX-ACCESS read-only
    STATUS current
    DESCRIPTION "Subordinate station name. Station 28."
    ::= { sentiaLOKStationNames 128 }

sentiaLOKStationName29 OBJECT-TYPE
    SYNTAX DisplayString
    MAX-ACCESS read-only
    STATUS current
    DESCRIPTION "Subordinate station name. Station 29."
    ::= { sentiaLOKStationNames 129 }

sentiaLOKStationName30 OBJECT-TYPE
    SYNTAX DisplayString
    MAX-ACCESS read-only
    STATUS current
    DESCRIPTION "Subordinate station name. Station 30."
    ::= { sentiaLOKStationNames 130 }

sentiaLOKStationName31 OBJECT-TYPE
    SYNTAX DisplayString
    MAX-ACCESS read-only
    STATUS current
    DESCRIPTION "Subordinate station name. Station 31."
    ::= { sentiaLOKStationNames 131 }

sentiaLOKStationName32 OBJECT-TYPE
    SYNTAX DisplayString
    MAX-ACCESS read-only
    STATUS current
    DESCRIPTION "Subordinate station name. Station 32."
    ::= { sentiaLOKStationNames 132 }

sentiaLOKStationCommStatuses OBJECT-IDENTITY
    STATUS current
    DESCRIPTION "sentiaLOK communication status values for stations 01..32; subidentifiers 101..132."
    ::= { strataonSentiaLOK 4 }

sentiaLOKStationCommStatus01 OBJECT-TYPE
    SYNTAX StrataonBinaryState
    MAX-ACCESS read-only
    STATUS current
    DESCRIPTION "Communication status: off(0)=offline, on(1)=online. Station 01."
    ::= { sentiaLOKStationCommStatuses 101 }

sentiaLOKStationCommStatus02 OBJECT-TYPE
    SYNTAX StrataonBinaryState
    MAX-ACCESS read-only
    STATUS current
    DESCRIPTION "Communication status: off(0)=offline, on(1)=online. Station 02."
    ::= { sentiaLOKStationCommStatuses 102 }

sentiaLOKStationCommStatus03 OBJECT-TYPE
    SYNTAX StrataonBinaryState
    MAX-ACCESS read-only
    STATUS current
    DESCRIPTION "Communication status: off(0)=offline, on(1)=online. Station 03."
    ::= { sentiaLOKStationCommStatuses 103 }

sentiaLOKStationCommStatus04 OBJECT-TYPE
    SYNTAX StrataonBinaryState
    MAX-ACCESS read-only
    STATUS current
    DESCRIPTION "Communication status: off(0)=offline, on(1)=online. Station 04."
    ::= { sentiaLOKStationCommStatuses 104 }

sentiaLOKStationCommStatus05 OBJECT-TYPE
    SYNTAX StrataonBinaryState
    MAX-ACCESS read-only
    STATUS current
    DESCRIPTION "Communication status: off(0)=offline, on(1)=online. Station 05."
    ::= { sentiaLOKStationCommStatuses 105 }

sentiaLOKStationCommStatus06 OBJECT-TYPE
    SYNTAX StrataonBinaryState
    MAX-ACCESS read-only
    STATUS current
    DESCRIPTION "Communication status: off(0)=offline, on(1)=online. Station 06."
    ::= { sentiaLOKStationCommStatuses 106 }

sentiaLOKStationCommStatus07 OBJECT-TYPE
    SYNTAX StrataonBinaryState
    MAX-ACCESS read-only
    STATUS current
    DESCRIPTION "Communication status: off(0)=offline, on(1)=online. Station 07."
    ::= { sentiaLOKStationCommStatuses 107 }

sentiaLOKStationCommStatus08 OBJECT-TYPE
    SYNTAX StrataonBinaryState
    MAX-ACCESS read-only
    STATUS current
    DESCRIPTION "Communication status: off(0)=offline, on(1)=online. Station 08."
    ::= { sentiaLOKStationCommStatuses 108 }

sentiaLOKStationCommStatus09 OBJECT-TYPE
    SYNTAX StrataonBinaryState
    MAX-ACCESS read-only
    STATUS current
    DESCRIPTION "Communication status: off(0)=offline, on(1)=online. Station 09."
    ::= { sentiaLOKStationCommStatuses 109 }

sentiaLOKStationCommStatus10 OBJECT-TYPE
    SYNTAX StrataonBinaryState
    MAX-ACCESS read-only
    STATUS current
    DESCRIPTION "Communication status: off(0)=offline, on(1)=online. Station 10."
    ::= { sentiaLOKStationCommStatuses 110 }

sentiaLOKStationCommStatus11 OBJECT-TYPE
    SYNTAX StrataonBinaryState
    MAX-ACCESS read-only
    STATUS current
    DESCRIPTION "Communication status: off(0)=offline, on(1)=online. Station 11."
    ::= { sentiaLOKStationCommStatuses 111 }

sentiaLOKStationCommStatus12 OBJECT-TYPE
    SYNTAX StrataonBinaryState
    MAX-ACCESS read-only
    STATUS current
    DESCRIPTION "Communication status: off(0)=offline, on(1)=online. Station 12."
    ::= { sentiaLOKStationCommStatuses 112 }

sentiaLOKStationCommStatus13 OBJECT-TYPE
    SYNTAX StrataonBinaryState
    MAX-ACCESS read-only
    STATUS current
    DESCRIPTION "Communication status: off(0)=offline, on(1)=online. Station 13."
    ::= { sentiaLOKStationCommStatuses 113 }

sentiaLOKStationCommStatus14 OBJECT-TYPE
    SYNTAX StrataonBinaryState
    MAX-ACCESS read-only
    STATUS current
    DESCRIPTION "Communication status: off(0)=offline, on(1)=online. Station 14."
    ::= { sentiaLOKStationCommStatuses 114 }

sentiaLOKStationCommStatus15 OBJECT-TYPE
    SYNTAX StrataonBinaryState
    MAX-ACCESS read-only
    STATUS current
    DESCRIPTION "Communication status: off(0)=offline, on(1)=online. Station 15."
    ::= { sentiaLOKStationCommStatuses 115 }

sentiaLOKStationCommStatus16 OBJECT-TYPE
    SYNTAX StrataonBinaryState
    MAX-ACCESS read-only
    STATUS current
    DESCRIPTION "Communication status: off(0)=offline, on(1)=online. Station 16."
    ::= { sentiaLOKStationCommStatuses 116 }

sentiaLOKStationCommStatus17 OBJECT-TYPE
    SYNTAX StrataonBinaryState
    MAX-ACCESS read-only
    STATUS current
    DESCRIPTION "Communication status: off(0)=offline, on(1)=online. Station 17."
    ::= { sentiaLOKStationCommStatuses 117 }

sentiaLOKStationCommStatus18 OBJECT-TYPE
    SYNTAX StrataonBinaryState
    MAX-ACCESS read-only
    STATUS current
    DESCRIPTION "Communication status: off(0)=offline, on(1)=online. Station 18."
    ::= { sentiaLOKStationCommStatuses 118 }

sentiaLOKStationCommStatus19 OBJECT-TYPE
    SYNTAX StrataonBinaryState
    MAX-ACCESS read-only
    STATUS current
    DESCRIPTION "Communication status: off(0)=offline, on(1)=online. Station 19."
    ::= { sentiaLOKStationCommStatuses 119 }

sentiaLOKStationCommStatus20 OBJECT-TYPE
    SYNTAX StrataonBinaryState
    MAX-ACCESS read-only
    STATUS current
    DESCRIPTION "Communication status: off(0)=offline, on(1)=online. Station 20."
    ::= { sentiaLOKStationCommStatuses 120 }

sentiaLOKStationCommStatus21 OBJECT-TYPE
    SYNTAX StrataonBinaryState
    MAX-ACCESS read-only
    STATUS current
    DESCRIPTION "Communication status: off(0)=offline, on(1)=online. Station 21."
    ::= { sentiaLOKStationCommStatuses 121 }

sentiaLOKStationCommStatus22 OBJECT-TYPE
    SYNTAX StrataonBinaryState
    MAX-ACCESS read-only
    STATUS current
    DESCRIPTION "Communication status: off(0)=offline, on(1)=online. Station 22."
    ::= { sentiaLOKStationCommStatuses 122 }

sentiaLOKStationCommStatus23 OBJECT-TYPE
    SYNTAX StrataonBinaryState
    MAX-ACCESS read-only
    STATUS current
    DESCRIPTION "Communication status: off(0)=offline, on(1)=online. Station 23."
    ::= { sentiaLOKStationCommStatuses 123 }

sentiaLOKStationCommStatus24 OBJECT-TYPE
    SYNTAX StrataonBinaryState
    MAX-ACCESS read-only
    STATUS current
    DESCRIPTION "Communication status: off(0)=offline, on(1)=online. Station 24."
    ::= { sentiaLOKStationCommStatuses 124 }

sentiaLOKStationCommStatus25 OBJECT-TYPE
    SYNTAX StrataonBinaryState
    MAX-ACCESS read-only
    STATUS current
    DESCRIPTION "Communication status: off(0)=offline, on(1)=online. Station 25."
    ::= { sentiaLOKStationCommStatuses 125 }

sentiaLOKStationCommStatus26 OBJECT-TYPE
    SYNTAX StrataonBinaryState
    MAX-ACCESS read-only
    STATUS current
    DESCRIPTION "Communication status: off(0)=offline, on(1)=online. Station 26."
    ::= { sentiaLOKStationCommStatuses 126 }

sentiaLOKStationCommStatus27 OBJECT-TYPE
    SYNTAX StrataonBinaryState
    MAX-ACCESS read-only
    STATUS current
    DESCRIPTION "Communication status: off(0)=offline, on(1)=online. Station 27."
    ::= { sentiaLOKStationCommStatuses 127 }

sentiaLOKStationCommStatus28 OBJECT-TYPE
    SYNTAX StrataonBinaryState
    MAX-ACCESS read-only
    STATUS current
    DESCRIPTION "Communication status: off(0)=offline, on(1)=online. Station 28."
    ::= { sentiaLOKStationCommStatuses 128 }

sentiaLOKStationCommStatus29 OBJECT-TYPE
    SYNTAX StrataonBinaryState
    MAX-ACCESS read-only
    STATUS current
    DESCRIPTION "Communication status: off(0)=offline, on(1)=online. Station 29."
    ::= { sentiaLOKStationCommStatuses 129 }

sentiaLOKStationCommStatus30 OBJECT-TYPE
    SYNTAX StrataonBinaryState
    MAX-ACCESS read-only
    STATUS current
    DESCRIPTION "Communication status: off(0)=offline, on(1)=online. Station 30."
    ::= { sentiaLOKStationCommStatuses 130 }

sentiaLOKStationCommStatus31 OBJECT-TYPE
    SYNTAX StrataonBinaryState
    MAX-ACCESS read-only
    STATUS current
    DESCRIPTION "Communication status: off(0)=offline, on(1)=online. Station 31."
    ::= { sentiaLOKStationCommStatuses 131 }

sentiaLOKStationCommStatus32 OBJECT-TYPE
    SYNTAX StrataonBinaryState
    MAX-ACCESS read-only
    STATUS current
    DESCRIPTION "Communication status: off(0)=offline, on(1)=online. Station 32."
    ::= { sentiaLOKStationCommStatuses 132 }

sentiaLOKStationFirmwares OBJECT-IDENTITY
    STATUS current
    DESCRIPTION "sentiaLOK firmware values for stations 01..32; subidentifiers 101..132."
    ::= { strataonSentiaLOK 5 }

sentiaLOKStationFirmware01 OBJECT-TYPE
    SYNTAX DisplayString
    MAX-ACCESS read-only
    STATUS current
    DESCRIPTION "Subordinate station firmware version. Station 01."
    ::= { sentiaLOKStationFirmwares 101 }

sentiaLOKStationFirmware02 OBJECT-TYPE
    SYNTAX DisplayString
    MAX-ACCESS read-only
    STATUS current
    DESCRIPTION "Subordinate station firmware version. Station 02."
    ::= { sentiaLOKStationFirmwares 102 }

sentiaLOKStationFirmware03 OBJECT-TYPE
    SYNTAX DisplayString
    MAX-ACCESS read-only
    STATUS current
    DESCRIPTION "Subordinate station firmware version. Station 03."
    ::= { sentiaLOKStationFirmwares 103 }

sentiaLOKStationFirmware04 OBJECT-TYPE
    SYNTAX DisplayString
    MAX-ACCESS read-only
    STATUS current
    DESCRIPTION "Subordinate station firmware version. Station 04."
    ::= { sentiaLOKStationFirmwares 104 }

sentiaLOKStationFirmware05 OBJECT-TYPE
    SYNTAX DisplayString
    MAX-ACCESS read-only
    STATUS current
    DESCRIPTION "Subordinate station firmware version. Station 05."
    ::= { sentiaLOKStationFirmwares 105 }

sentiaLOKStationFirmware06 OBJECT-TYPE
    SYNTAX DisplayString
    MAX-ACCESS read-only
    STATUS current
    DESCRIPTION "Subordinate station firmware version. Station 06."
    ::= { sentiaLOKStationFirmwares 106 }

sentiaLOKStationFirmware07 OBJECT-TYPE
    SYNTAX DisplayString
    MAX-ACCESS read-only
    STATUS current
    DESCRIPTION "Subordinate station firmware version. Station 07."
    ::= { sentiaLOKStationFirmwares 107 }

sentiaLOKStationFirmware08 OBJECT-TYPE
    SYNTAX DisplayString
    MAX-ACCESS read-only
    STATUS current
    DESCRIPTION "Subordinate station firmware version. Station 08."
    ::= { sentiaLOKStationFirmwares 108 }

sentiaLOKStationFirmware09 OBJECT-TYPE
    SYNTAX DisplayString
    MAX-ACCESS read-only
    STATUS current
    DESCRIPTION "Subordinate station firmware version. Station 09."
    ::= { sentiaLOKStationFirmwares 109 }

sentiaLOKStationFirmware10 OBJECT-TYPE
    SYNTAX DisplayString
    MAX-ACCESS read-only
    STATUS current
    DESCRIPTION "Subordinate station firmware version. Station 10."
    ::= { sentiaLOKStationFirmwares 110 }

sentiaLOKStationFirmware11 OBJECT-TYPE
    SYNTAX DisplayString
    MAX-ACCESS read-only
    STATUS current
    DESCRIPTION "Subordinate station firmware version. Station 11."
    ::= { sentiaLOKStationFirmwares 111 }

sentiaLOKStationFirmware12 OBJECT-TYPE
    SYNTAX DisplayString
    MAX-ACCESS read-only
    STATUS current
    DESCRIPTION "Subordinate station firmware version. Station 12."
    ::= { sentiaLOKStationFirmwares 112 }

sentiaLOKStationFirmware13 OBJECT-TYPE
    SYNTAX DisplayString
    MAX-ACCESS read-only
    STATUS current
    DESCRIPTION "Subordinate station firmware version. Station 13."
    ::= { sentiaLOKStationFirmwares 113 }

sentiaLOKStationFirmware14 OBJECT-TYPE
    SYNTAX DisplayString
    MAX-ACCESS read-only
    STATUS current
    DESCRIPTION "Subordinate station firmware version. Station 14."
    ::= { sentiaLOKStationFirmwares 114 }

sentiaLOKStationFirmware15 OBJECT-TYPE
    SYNTAX DisplayString
    MAX-ACCESS read-only
    STATUS current
    DESCRIPTION "Subordinate station firmware version. Station 15."
    ::= { sentiaLOKStationFirmwares 115 }

sentiaLOKStationFirmware16 OBJECT-TYPE
    SYNTAX DisplayString
    MAX-ACCESS read-only
    STATUS current
    DESCRIPTION "Subordinate station firmware version. Station 16."
    ::= { sentiaLOKStationFirmwares 116 }

sentiaLOKStationFirmware17 OBJECT-TYPE
    SYNTAX DisplayString
    MAX-ACCESS read-only
    STATUS current
    DESCRIPTION "Subordinate station firmware version. Station 17."
    ::= { sentiaLOKStationFirmwares 117 }

sentiaLOKStationFirmware18 OBJECT-TYPE
    SYNTAX DisplayString
    MAX-ACCESS read-only
    STATUS current
    DESCRIPTION "Subordinate station firmware version. Station 18."
    ::= { sentiaLOKStationFirmwares 118 }

sentiaLOKStationFirmware19 OBJECT-TYPE
    SYNTAX DisplayString
    MAX-ACCESS read-only
    STATUS current
    DESCRIPTION "Subordinate station firmware version. Station 19."
    ::= { sentiaLOKStationFirmwares 119 }

sentiaLOKStationFirmware20 OBJECT-TYPE
    SYNTAX DisplayString
    MAX-ACCESS read-only
    STATUS current
    DESCRIPTION "Subordinate station firmware version. Station 20."
    ::= { sentiaLOKStationFirmwares 120 }

sentiaLOKStationFirmware21 OBJECT-TYPE
    SYNTAX DisplayString
    MAX-ACCESS read-only
    STATUS current
    DESCRIPTION "Subordinate station firmware version. Station 21."
    ::= { sentiaLOKStationFirmwares 121 }

sentiaLOKStationFirmware22 OBJECT-TYPE
    SYNTAX DisplayString
    MAX-ACCESS read-only
    STATUS current
    DESCRIPTION "Subordinate station firmware version. Station 22."
    ::= { sentiaLOKStationFirmwares 122 }

sentiaLOKStationFirmware23 OBJECT-TYPE
    SYNTAX DisplayString
    MAX-ACCESS read-only
    STATUS current
    DESCRIPTION "Subordinate station firmware version. Station 23."
    ::= { sentiaLOKStationFirmwares 123 }

sentiaLOKStationFirmware24 OBJECT-TYPE
    SYNTAX DisplayString
    MAX-ACCESS read-only
    STATUS current
    DESCRIPTION "Subordinate station firmware version. Station 24."
    ::= { sentiaLOKStationFirmwares 124 }

sentiaLOKStationFirmware25 OBJECT-TYPE
    SYNTAX DisplayString
    MAX-ACCESS read-only
    STATUS current
    DESCRIPTION "Subordinate station firmware version. Station 25."
    ::= { sentiaLOKStationFirmwares 125 }

sentiaLOKStationFirmware26 OBJECT-TYPE
    SYNTAX DisplayString
    MAX-ACCESS read-only
    STATUS current
    DESCRIPTION "Subordinate station firmware version. Station 26."
    ::= { sentiaLOKStationFirmwares 126 }

sentiaLOKStationFirmware27 OBJECT-TYPE
    SYNTAX DisplayString
    MAX-ACCESS read-only
    STATUS current
    DESCRIPTION "Subordinate station firmware version. Station 27."
    ::= { sentiaLOKStationFirmwares 127 }

sentiaLOKStationFirmware28 OBJECT-TYPE
    SYNTAX DisplayString
    MAX-ACCESS read-only
    STATUS current
    DESCRIPTION "Subordinate station firmware version. Station 28."
    ::= { sentiaLOKStationFirmwares 128 }

sentiaLOKStationFirmware29 OBJECT-TYPE
    SYNTAX DisplayString
    MAX-ACCESS read-only
    STATUS current
    DESCRIPTION "Subordinate station firmware version. Station 29."
    ::= { sentiaLOKStationFirmwares 129 }

sentiaLOKStationFirmware30 OBJECT-TYPE
    SYNTAX DisplayString
    MAX-ACCESS read-only
    STATUS current
    DESCRIPTION "Subordinate station firmware version. Station 30."
    ::= { sentiaLOKStationFirmwares 130 }

sentiaLOKStationFirmware31 OBJECT-TYPE
    SYNTAX DisplayString
    MAX-ACCESS read-only
    STATUS current
    DESCRIPTION "Subordinate station firmware version. Station 31."
    ::= { sentiaLOKStationFirmwares 131 }

sentiaLOKStationFirmware32 OBJECT-TYPE
    SYNTAX DisplayString
    MAX-ACCESS read-only
    STATUS current
    DESCRIPTION "Subordinate station firmware version. Station 32."
    ::= { sentiaLOKStationFirmwares 132 }

sentiaLOKStationDeviceTypes OBJECT-IDENTITY
    STATUS current
    DESCRIPTION "sentiaLOK device type values for stations 01..32; subidentifiers 101..132."
    ::= { strataonSentiaLOK 6 }

sentiaLOKStationDeviceType01 OBJECT-TYPE
    SYNTAX Integer32
    MAX-ACCESS read-only
    STATUS current
    DESCRIPTION "Device type reported by subordinate station. Station 01."
    ::= { sentiaLOKStationDeviceTypes 101 }

sentiaLOKStationDeviceType02 OBJECT-TYPE
    SYNTAX Integer32
    MAX-ACCESS read-only
    STATUS current
    DESCRIPTION "Device type reported by subordinate station. Station 02."
    ::= { sentiaLOKStationDeviceTypes 102 }

sentiaLOKStationDeviceType03 OBJECT-TYPE
    SYNTAX Integer32
    MAX-ACCESS read-only
    STATUS current
    DESCRIPTION "Device type reported by subordinate station. Station 03."
    ::= { sentiaLOKStationDeviceTypes 103 }

sentiaLOKStationDeviceType04 OBJECT-TYPE
    SYNTAX Integer32
    MAX-ACCESS read-only
    STATUS current
    DESCRIPTION "Device type reported by subordinate station. Station 04."
    ::= { sentiaLOKStationDeviceTypes 104 }

sentiaLOKStationDeviceType05 OBJECT-TYPE
    SYNTAX Integer32
    MAX-ACCESS read-only
    STATUS current
    DESCRIPTION "Device type reported by subordinate station. Station 05."
    ::= { sentiaLOKStationDeviceTypes 105 }

sentiaLOKStationDeviceType06 OBJECT-TYPE
    SYNTAX Integer32
    MAX-ACCESS read-only
    STATUS current
    DESCRIPTION "Device type reported by subordinate station. Station 06."
    ::= { sentiaLOKStationDeviceTypes 106 }

sentiaLOKStationDeviceType07 OBJECT-TYPE
    SYNTAX Integer32
    MAX-ACCESS read-only
    STATUS current
    DESCRIPTION "Device type reported by subordinate station. Station 07."
    ::= { sentiaLOKStationDeviceTypes 107 }

sentiaLOKStationDeviceType08 OBJECT-TYPE
    SYNTAX Integer32
    MAX-ACCESS read-only
    STATUS current
    DESCRIPTION "Device type reported by subordinate station. Station 08."
    ::= { sentiaLOKStationDeviceTypes 108 }

sentiaLOKStationDeviceType09 OBJECT-TYPE
    SYNTAX Integer32
    MAX-ACCESS read-only
    STATUS current
    DESCRIPTION "Device type reported by subordinate station. Station 09."
    ::= { sentiaLOKStationDeviceTypes 109 }

sentiaLOKStationDeviceType10 OBJECT-TYPE
    SYNTAX Integer32
    MAX-ACCESS read-only
    STATUS current
    DESCRIPTION "Device type reported by subordinate station. Station 10."
    ::= { sentiaLOKStationDeviceTypes 110 }

sentiaLOKStationDeviceType11 OBJECT-TYPE
    SYNTAX Integer32
    MAX-ACCESS read-only
    STATUS current
    DESCRIPTION "Device type reported by subordinate station. Station 11."
    ::= { sentiaLOKStationDeviceTypes 111 }

sentiaLOKStationDeviceType12 OBJECT-TYPE
    SYNTAX Integer32
    MAX-ACCESS read-only
    STATUS current
    DESCRIPTION "Device type reported by subordinate station. Station 12."
    ::= { sentiaLOKStationDeviceTypes 112 }

sentiaLOKStationDeviceType13 OBJECT-TYPE
    SYNTAX Integer32
    MAX-ACCESS read-only
    STATUS current
    DESCRIPTION "Device type reported by subordinate station. Station 13."
    ::= { sentiaLOKStationDeviceTypes 113 }

sentiaLOKStationDeviceType14 OBJECT-TYPE
    SYNTAX Integer32
    MAX-ACCESS read-only
    STATUS current
    DESCRIPTION "Device type reported by subordinate station. Station 14."
    ::= { sentiaLOKStationDeviceTypes 114 }

sentiaLOKStationDeviceType15 OBJECT-TYPE
    SYNTAX Integer32
    MAX-ACCESS read-only
    STATUS current
    DESCRIPTION "Device type reported by subordinate station. Station 15."
    ::= { sentiaLOKStationDeviceTypes 115 }

sentiaLOKStationDeviceType16 OBJECT-TYPE
    SYNTAX Integer32
    MAX-ACCESS read-only
    STATUS current
    DESCRIPTION "Device type reported by subordinate station. Station 16."
    ::= { sentiaLOKStationDeviceTypes 116 }

sentiaLOKStationDeviceType17 OBJECT-TYPE
    SYNTAX Integer32
    MAX-ACCESS read-only
    STATUS current
    DESCRIPTION "Device type reported by subordinate station. Station 17."
    ::= { sentiaLOKStationDeviceTypes 117 }

sentiaLOKStationDeviceType18 OBJECT-TYPE
    SYNTAX Integer32
    MAX-ACCESS read-only
    STATUS current
    DESCRIPTION "Device type reported by subordinate station. Station 18."
    ::= { sentiaLOKStationDeviceTypes 118 }

sentiaLOKStationDeviceType19 OBJECT-TYPE
    SYNTAX Integer32
    MAX-ACCESS read-only
    STATUS current
    DESCRIPTION "Device type reported by subordinate station. Station 19."
    ::= { sentiaLOKStationDeviceTypes 119 }

sentiaLOKStationDeviceType20 OBJECT-TYPE
    SYNTAX Integer32
    MAX-ACCESS read-only
    STATUS current
    DESCRIPTION "Device type reported by subordinate station. Station 20."
    ::= { sentiaLOKStationDeviceTypes 120 }

sentiaLOKStationDeviceType21 OBJECT-TYPE
    SYNTAX Integer32
    MAX-ACCESS read-only
    STATUS current
    DESCRIPTION "Device type reported by subordinate station. Station 21."
    ::= { sentiaLOKStationDeviceTypes 121 }

sentiaLOKStationDeviceType22 OBJECT-TYPE
    SYNTAX Integer32
    MAX-ACCESS read-only
    STATUS current
    DESCRIPTION "Device type reported by subordinate station. Station 22."
    ::= { sentiaLOKStationDeviceTypes 122 }

sentiaLOKStationDeviceType23 OBJECT-TYPE
    SYNTAX Integer32
    MAX-ACCESS read-only
    STATUS current
    DESCRIPTION "Device type reported by subordinate station. Station 23."
    ::= { sentiaLOKStationDeviceTypes 123 }

sentiaLOKStationDeviceType24 OBJECT-TYPE
    SYNTAX Integer32
    MAX-ACCESS read-only
    STATUS current
    DESCRIPTION "Device type reported by subordinate station. Station 24."
    ::= { sentiaLOKStationDeviceTypes 124 }

sentiaLOKStationDeviceType25 OBJECT-TYPE
    SYNTAX Integer32
    MAX-ACCESS read-only
    STATUS current
    DESCRIPTION "Device type reported by subordinate station. Station 25."
    ::= { sentiaLOKStationDeviceTypes 125 }

sentiaLOKStationDeviceType26 OBJECT-TYPE
    SYNTAX Integer32
    MAX-ACCESS read-only
    STATUS current
    DESCRIPTION "Device type reported by subordinate station. Station 26."
    ::= { sentiaLOKStationDeviceTypes 126 }

sentiaLOKStationDeviceType27 OBJECT-TYPE
    SYNTAX Integer32
    MAX-ACCESS read-only
    STATUS current
    DESCRIPTION "Device type reported by subordinate station. Station 27."
    ::= { sentiaLOKStationDeviceTypes 127 }

sentiaLOKStationDeviceType28 OBJECT-TYPE
    SYNTAX Integer32
    MAX-ACCESS read-only
    STATUS current
    DESCRIPTION "Device type reported by subordinate station. Station 28."
    ::= { sentiaLOKStationDeviceTypes 128 }

sentiaLOKStationDeviceType29 OBJECT-TYPE
    SYNTAX Integer32
    MAX-ACCESS read-only
    STATUS current
    DESCRIPTION "Device type reported by subordinate station. Station 29."
    ::= { sentiaLOKStationDeviceTypes 129 }

sentiaLOKStationDeviceType30 OBJECT-TYPE
    SYNTAX Integer32
    MAX-ACCESS read-only
    STATUS current
    DESCRIPTION "Device type reported by subordinate station. Station 30."
    ::= { sentiaLOKStationDeviceTypes 130 }

sentiaLOKStationDeviceType31 OBJECT-TYPE
    SYNTAX Integer32
    MAX-ACCESS read-only
    STATUS current
    DESCRIPTION "Device type reported by subordinate station. Station 31."
    ::= { sentiaLOKStationDeviceTypes 131 }

sentiaLOKStationDeviceType32 OBJECT-TYPE
    SYNTAX Integer32
    MAX-ACCESS read-only
    STATUS current
    DESCRIPTION "Device type reported by subordinate station. Station 32."
    ::= { sentiaLOKStationDeviceTypes 132 }

sentiaLOKInput01States OBJECT-IDENTITY
    STATUS current
    DESCRIPTION "sentiaLOK digital input 01 state for stations 01..32; subidentifiers 101..132."
    ::= { strataonSentiaLOK 7 }

sentiaLOKInput01State01 OBJECT-TYPE
    SYNTAX StrataonBinaryState
    MAX-ACCESS read-only
    STATUS current
    DESCRIPTION "Digital input 01 state. Station 01."
    ::= { sentiaLOKInput01States 101 }

sentiaLOKInput01State02 OBJECT-TYPE
    SYNTAX StrataonBinaryState
    MAX-ACCESS read-only
    STATUS current
    DESCRIPTION "Digital input 01 state. Station 02."
    ::= { sentiaLOKInput01States 102 }

sentiaLOKInput01State03 OBJECT-TYPE
    SYNTAX StrataonBinaryState
    MAX-ACCESS read-only
    STATUS current
    DESCRIPTION "Digital input 01 state. Station 03."
    ::= { sentiaLOKInput01States 103 }

sentiaLOKInput01State04 OBJECT-TYPE
    SYNTAX StrataonBinaryState
    MAX-ACCESS read-only
    STATUS current
    DESCRIPTION "Digital input 01 state. Station 04."
    ::= { sentiaLOKInput01States 104 }

sentiaLOKInput01State05 OBJECT-TYPE
    SYNTAX StrataonBinaryState
    MAX-ACCESS read-only
    STATUS current
    DESCRIPTION "Digital input 01 state. Station 05."
    ::= { sentiaLOKInput01States 105 }

sentiaLOKInput01State06 OBJECT-TYPE
    SYNTAX StrataonBinaryState
    MAX-ACCESS read-only
    STATUS current
    DESCRIPTION "Digital input 01 state. Station 06."
    ::= { sentiaLOKInput01States 106 }

sentiaLOKInput01State07 OBJECT-TYPE
    SYNTAX StrataonBinaryState
    MAX-ACCESS read-only
    STATUS current
    DESCRIPTION "Digital input 01 state. Station 07."
    ::= { sentiaLOKInput01States 107 }

sentiaLOKInput01State08 OBJECT-TYPE
    SYNTAX StrataonBinaryState
    MAX-ACCESS read-only
    STATUS current
    DESCRIPTION "Digital input 01 state. Station 08."
    ::= { sentiaLOKInput01States 108 }

sentiaLOKInput01State09 OBJECT-TYPE
    SYNTAX StrataonBinaryState
    MAX-ACCESS read-only
    STATUS current
    DESCRIPTION "Digital input 01 state. Station 09."
    ::= { sentiaLOKInput01States 109 }

sentiaLOKInput01State10 OBJECT-TYPE
    SYNTAX StrataonBinaryState
    MAX-ACCESS read-only
    STATUS current
    DESCRIPTION "Digital input 01 state. Station 10."
    ::= { sentiaLOKInput01States 110 }

sentiaLOKInput01State11 OBJECT-TYPE
    SYNTAX StrataonBinaryState
    MAX-ACCESS read-only
    STATUS current
    DESCRIPTION "Digital input 01 state. Station 11."
    ::= { sentiaLOKInput01States 111 }

sentiaLOKInput01State12 OBJECT-TYPE
    SYNTAX StrataonBinaryState
    MAX-ACCESS read-only
    STATUS current
    DESCRIPTION "Digital input 01 state. Station 12."
    ::= { sentiaLOKInput01States 112 }

sentiaLOKInput01State13 OBJECT-TYPE
    SYNTAX StrataonBinaryState
    MAX-ACCESS read-only
    STATUS current
    DESCRIPTION "Digital input 01 state. Station 13."
    ::= { sentiaLOKInput01States 113 }

sentiaLOKInput01State14 OBJECT-TYPE
    SYNTAX StrataonBinaryState
    MAX-ACCESS read-only
    STATUS current
    DESCRIPTION "Digital input 01 state. Station 14."
    ::= { sentiaLOKInput01States 114 }

sentiaLOKInput01State15 OBJECT-TYPE
    SYNTAX StrataonBinaryState
    MAX-ACCESS read-only
    STATUS current
    DESCRIPTION "Digital input 01 state. Station 15."
    ::= { sentiaLOKInput01States 115 }

sentiaLOKInput01State16 OBJECT-TYPE
    SYNTAX StrataonBinaryState
    MAX-ACCESS read-only
    STATUS current
    DESCRIPTION "Digital input 01 state. Station 16."
    ::= { sentiaLOKInput01States 116 }

sentiaLOKInput01State17 OBJECT-TYPE
    SYNTAX StrataonBinaryState
    MAX-ACCESS read-only
    STATUS current
    DESCRIPTION "Digital input 01 state. Station 17."
    ::= { sentiaLOKInput01States 117 }

sentiaLOKInput01State18 OBJECT-TYPE
    SYNTAX StrataonBinaryState
    MAX-ACCESS read-only
    STATUS current
    DESCRIPTION "Digital input 01 state. Station 18."
    ::= { sentiaLOKInput01States 118 }

sentiaLOKInput01State19 OBJECT-TYPE
    SYNTAX StrataonBinaryState
    MAX-ACCESS read-only
    STATUS current
    DESCRIPTION "Digital input 01 state. Station 19."
    ::= { sentiaLOKInput01States 119 }

sentiaLOKInput01State20 OBJECT-TYPE
    SYNTAX StrataonBinaryState
    MAX-ACCESS read-only
    STATUS current
    DESCRIPTION "Digital input 01 state. Station 20."
    ::= { sentiaLOKInput01States 120 }

sentiaLOKInput01State21 OBJECT-TYPE
    SYNTAX StrataonBinaryState
    MAX-ACCESS read-only
    STATUS current
    DESCRIPTION "Digital input 01 state. Station 21."
    ::= { sentiaLOKInput01States 121 }

sentiaLOKInput01State22 OBJECT-TYPE
    SYNTAX StrataonBinaryState
    MAX-ACCESS read-only
    STATUS current
    DESCRIPTION "Digital input 01 state. Station 22."
    ::= { sentiaLOKInput01States 122 }

sentiaLOKInput01State23 OBJECT-TYPE
    SYNTAX StrataonBinaryState
    MAX-ACCESS read-only
    STATUS current
    DESCRIPTION "Digital input 01 state. Station 23."
    ::= { sentiaLOKInput01States 123 }

sentiaLOKInput01State24 OBJECT-TYPE
    SYNTAX StrataonBinaryState
    MAX-ACCESS read-only
    STATUS current
    DESCRIPTION "Digital input 01 state. Station 24."
    ::= { sentiaLOKInput01States 124 }

sentiaLOKInput01State25 OBJECT-TYPE
    SYNTAX StrataonBinaryState
    MAX-ACCESS read-only
    STATUS current
    DESCRIPTION "Digital input 01 state. Station 25."
    ::= { sentiaLOKInput01States 125 }

sentiaLOKInput01State26 OBJECT-TYPE
    SYNTAX StrataonBinaryState
    MAX-ACCESS read-only
    STATUS current
    DESCRIPTION "Digital input 01 state. Station 26."
    ::= { sentiaLOKInput01States 126 }

sentiaLOKInput01State27 OBJECT-TYPE
    SYNTAX StrataonBinaryState
    MAX-ACCESS read-only
    STATUS current
    DESCRIPTION "Digital input 01 state. Station 27."
    ::= { sentiaLOKInput01States 127 }

sentiaLOKInput01State28 OBJECT-TYPE
    SYNTAX StrataonBinaryState
    MAX-ACCESS read-only
    STATUS current
    DESCRIPTION "Digital input 01 state. Station 28."
    ::= { sentiaLOKInput01States 128 }

sentiaLOKInput01State29 OBJECT-TYPE
    SYNTAX StrataonBinaryState
    MAX-ACCESS read-only
    STATUS current
    DESCRIPTION "Digital input 01 state. Station 29."
    ::= { sentiaLOKInput01States 129 }

sentiaLOKInput01State30 OBJECT-TYPE
    SYNTAX StrataonBinaryState
    MAX-ACCESS read-only
    STATUS current
    DESCRIPTION "Digital input 01 state. Station 30."
    ::= { sentiaLOKInput01States 130 }

sentiaLOKInput01State31 OBJECT-TYPE
    SYNTAX StrataonBinaryState
    MAX-ACCESS read-only
    STATUS current
    DESCRIPTION "Digital input 01 state. Station 31."
    ::= { sentiaLOKInput01States 131 }

sentiaLOKInput01State32 OBJECT-TYPE
    SYNTAX StrataonBinaryState
    MAX-ACCESS read-only
    STATUS current
    DESCRIPTION "Digital input 01 state. Station 32."
    ::= { sentiaLOKInput01States 132 }

sentiaLOKInput02States OBJECT-IDENTITY
    STATUS current
    DESCRIPTION "sentiaLOK digital input 02 state for stations 01..32; subidentifiers 101..132."
    ::= { strataonSentiaLOK 8 }

sentiaLOKInput02State01 OBJECT-TYPE
    SYNTAX StrataonBinaryState
    MAX-ACCESS read-only
    STATUS current
    DESCRIPTION "Digital input 02 state. Station 01."
    ::= { sentiaLOKInput02States 101 }

sentiaLOKInput02State02 OBJECT-TYPE
    SYNTAX StrataonBinaryState
    MAX-ACCESS read-only
    STATUS current
    DESCRIPTION "Digital input 02 state. Station 02."
    ::= { sentiaLOKInput02States 102 }

sentiaLOKInput02State03 OBJECT-TYPE
    SYNTAX StrataonBinaryState
    MAX-ACCESS read-only
    STATUS current
    DESCRIPTION "Digital input 02 state. Station 03."
    ::= { sentiaLOKInput02States 103 }

sentiaLOKInput02State04 OBJECT-TYPE
    SYNTAX StrataonBinaryState
    MAX-ACCESS read-only
    STATUS current
    DESCRIPTION "Digital input 02 state. Station 04."
    ::= { sentiaLOKInput02States 104 }

sentiaLOKInput02State05 OBJECT-TYPE
    SYNTAX StrataonBinaryState
    MAX-ACCESS read-only
    STATUS current
    DESCRIPTION "Digital input 02 state. Station 05."
    ::= { sentiaLOKInput02States 105 }

sentiaLOKInput02State06 OBJECT-TYPE
    SYNTAX StrataonBinaryState
    MAX-ACCESS read-only
    STATUS current
    DESCRIPTION "Digital input 02 state. Station 06."
    ::= { sentiaLOKInput02States 106 }

sentiaLOKInput02State07 OBJECT-TYPE
    SYNTAX StrataonBinaryState
    MAX-ACCESS read-only
    STATUS current
    DESCRIPTION "Digital input 02 state. Station 07."
    ::= { sentiaLOKInput02States 107 }

sentiaLOKInput02State08 OBJECT-TYPE
    SYNTAX StrataonBinaryState
    MAX-ACCESS read-only
    STATUS current
    DESCRIPTION "Digital input 02 state. Station 08."
    ::= { sentiaLOKInput02States 108 }

sentiaLOKInput02State09 OBJECT-TYPE
    SYNTAX StrataonBinaryState
    MAX-ACCESS read-only
    STATUS current
    DESCRIPTION "Digital input 02 state. Station 09."
    ::= { sentiaLOKInput02States 109 }

sentiaLOKInput02State10 OBJECT-TYPE
    SYNTAX StrataonBinaryState
    MAX-ACCESS read-only
    STATUS current
    DESCRIPTION "Digital input 02 state. Station 10."
    ::= { sentiaLOKInput02States 110 }

sentiaLOKInput02State11 OBJECT-TYPE
    SYNTAX StrataonBinaryState
    MAX-ACCESS read-only
    STATUS current
    DESCRIPTION "Digital input 02 state. Station 11."
    ::= { sentiaLOKInput02States 111 }

sentiaLOKInput02State12 OBJECT-TYPE
    SYNTAX StrataonBinaryState
    MAX-ACCESS read-only
    STATUS current
    DESCRIPTION "Digital input 02 state. Station 12."
    ::= { sentiaLOKInput02States 112 }

sentiaLOKInput02State13 OBJECT-TYPE
    SYNTAX StrataonBinaryState
    MAX-ACCESS read-only
    STATUS current
    DESCRIPTION "Digital input 02 state. Station 13."
    ::= { sentiaLOKInput02States 113 }

sentiaLOKInput02State14 OBJECT-TYPE
    SYNTAX StrataonBinaryState
    MAX-ACCESS read-only
    STATUS current
    DESCRIPTION "Digital input 02 state. Station 14."
    ::= { sentiaLOKInput02States 114 }

sentiaLOKInput02State15 OBJECT-TYPE
    SYNTAX StrataonBinaryState
    MAX-ACCESS read-only
    STATUS current
    DESCRIPTION "Digital input 02 state. Station 15."
    ::= { sentiaLOKInput02States 115 }

sentiaLOKInput02State16 OBJECT-TYPE
    SYNTAX StrataonBinaryState
    MAX-ACCESS read-only
    STATUS current
    DESCRIPTION "Digital input 02 state. Station 16."
    ::= { sentiaLOKInput02States 116 }

sentiaLOKInput02State17 OBJECT-TYPE
    SYNTAX StrataonBinaryState
    MAX-ACCESS read-only
    STATUS current
    DESCRIPTION "Digital input 02 state. Station 17."
    ::= { sentiaLOKInput02States 117 }

sentiaLOKInput02State18 OBJECT-TYPE
    SYNTAX StrataonBinaryState
    MAX-ACCESS read-only
    STATUS current
    DESCRIPTION "Digital input 02 state. Station 18."
    ::= { sentiaLOKInput02States 118 }

sentiaLOKInput02State19 OBJECT-TYPE
    SYNTAX StrataonBinaryState
    MAX-ACCESS read-only
    STATUS current
    DESCRIPTION "Digital input 02 state. Station 19."
    ::= { sentiaLOKInput02States 119 }

sentiaLOKInput02State20 OBJECT-TYPE
    SYNTAX StrataonBinaryState
    MAX-ACCESS read-only
    STATUS current
    DESCRIPTION "Digital input 02 state. Station 20."
    ::= { sentiaLOKInput02States 120 }

sentiaLOKInput02State21 OBJECT-TYPE
    SYNTAX StrataonBinaryState
    MAX-ACCESS read-only
    STATUS current
    DESCRIPTION "Digital input 02 state. Station 21."
    ::= { sentiaLOKInput02States 121 }

sentiaLOKInput02State22 OBJECT-TYPE
    SYNTAX StrataonBinaryState
    MAX-ACCESS read-only
    STATUS current
    DESCRIPTION "Digital input 02 state. Station 22."
    ::= { sentiaLOKInput02States 122 }

sentiaLOKInput02State23 OBJECT-TYPE
    SYNTAX StrataonBinaryState
    MAX-ACCESS read-only
    STATUS current
    DESCRIPTION "Digital input 02 state. Station 23."
    ::= { sentiaLOKInput02States 123 }

sentiaLOKInput02State24 OBJECT-TYPE
    SYNTAX StrataonBinaryState
    MAX-ACCESS read-only
    STATUS current
    DESCRIPTION "Digital input 02 state. Station 24."
    ::= { sentiaLOKInput02States 124 }

sentiaLOKInput02State25 OBJECT-TYPE
    SYNTAX StrataonBinaryState
    MAX-ACCESS read-only
    STATUS current
    DESCRIPTION "Digital input 02 state. Station 25."
    ::= { sentiaLOKInput02States 125 }

sentiaLOKInput02State26 OBJECT-TYPE
    SYNTAX StrataonBinaryState
    MAX-ACCESS read-only
    STATUS current
    DESCRIPTION "Digital input 02 state. Station 26."
    ::= { sentiaLOKInput02States 126 }

sentiaLOKInput02State27 OBJECT-TYPE
    SYNTAX StrataonBinaryState
    MAX-ACCESS read-only
    STATUS current
    DESCRIPTION "Digital input 02 state. Station 27."
    ::= { sentiaLOKInput02States 127 }

sentiaLOKInput02State28 OBJECT-TYPE
    SYNTAX StrataonBinaryState
    MAX-ACCESS read-only
    STATUS current
    DESCRIPTION "Digital input 02 state. Station 28."
    ::= { sentiaLOKInput02States 128 }

sentiaLOKInput02State29 OBJECT-TYPE
    SYNTAX StrataonBinaryState
    MAX-ACCESS read-only
    STATUS current
    DESCRIPTION "Digital input 02 state. Station 29."
    ::= { sentiaLOKInput02States 129 }

sentiaLOKInput02State30 OBJECT-TYPE
    SYNTAX StrataonBinaryState
    MAX-ACCESS read-only
    STATUS current
    DESCRIPTION "Digital input 02 state. Station 30."
    ::= { sentiaLOKInput02States 130 }

sentiaLOKInput02State31 OBJECT-TYPE
    SYNTAX StrataonBinaryState
    MAX-ACCESS read-only
    STATUS current
    DESCRIPTION "Digital input 02 state. Station 31."
    ::= { sentiaLOKInput02States 131 }

sentiaLOKInput02State32 OBJECT-TYPE
    SYNTAX StrataonBinaryState
    MAX-ACCESS read-only
    STATUS current
    DESCRIPTION "Digital input 02 state. Station 32."
    ::= { sentiaLOKInput02States 132 }

sentiaLOKInput03States OBJECT-IDENTITY
    STATUS current
    DESCRIPTION "sentiaLOK digital input 03 state for stations 01..32; subidentifiers 101..132."
    ::= { strataonSentiaLOK 9 }

sentiaLOKInput03State01 OBJECT-TYPE
    SYNTAX StrataonBinaryState
    MAX-ACCESS read-only
    STATUS current
    DESCRIPTION "Digital input 03 state. Station 01."
    ::= { sentiaLOKInput03States 101 }

sentiaLOKInput03State02 OBJECT-TYPE
    SYNTAX StrataonBinaryState
    MAX-ACCESS read-only
    STATUS current
    DESCRIPTION "Digital input 03 state. Station 02."
    ::= { sentiaLOKInput03States 102 }

sentiaLOKInput03State03 OBJECT-TYPE
    SYNTAX StrataonBinaryState
    MAX-ACCESS read-only
    STATUS current
    DESCRIPTION "Digital input 03 state. Station 03."
    ::= { sentiaLOKInput03States 103 }

sentiaLOKInput03State04 OBJECT-TYPE
    SYNTAX StrataonBinaryState
    MAX-ACCESS read-only
    STATUS current
    DESCRIPTION "Digital input 03 state. Station 04."
    ::= { sentiaLOKInput03States 104 }

sentiaLOKInput03State05 OBJECT-TYPE
    SYNTAX StrataonBinaryState
    MAX-ACCESS read-only
    STATUS current
    DESCRIPTION "Digital input 03 state. Station 05."
    ::= { sentiaLOKInput03States 105 }

sentiaLOKInput03State06 OBJECT-TYPE
    SYNTAX StrataonBinaryState
    MAX-ACCESS read-only
    STATUS current
    DESCRIPTION "Digital input 03 state. Station 06."
    ::= { sentiaLOKInput03States 106 }

sentiaLOKInput03State07 OBJECT-TYPE
    SYNTAX StrataonBinaryState
    MAX-ACCESS read-only
    STATUS current
    DESCRIPTION "Digital input 03 state. Station 07."
    ::= { sentiaLOKInput03States 107 }

sentiaLOKInput03State08 OBJECT-TYPE
    SYNTAX StrataonBinaryState
    MAX-ACCESS read-only
    STATUS current
    DESCRIPTION "Digital input 03 state. Station 08."
    ::= { sentiaLOKInput03States 108 }

sentiaLOKInput03State09 OBJECT-TYPE
    SYNTAX StrataonBinaryState
    MAX-ACCESS read-only
    STATUS current
    DESCRIPTION "Digital input 03 state. Station 09."
    ::= { sentiaLOKInput03States 109 }

sentiaLOKInput03State10 OBJECT-TYPE
    SYNTAX StrataonBinaryState
    MAX-ACCESS read-only
    STATUS current
    DESCRIPTION "Digital input 03 state. Station 10."
    ::= { sentiaLOKInput03States 110 }

sentiaLOKInput03State11 OBJECT-TYPE
    SYNTAX StrataonBinaryState
    MAX-ACCESS read-only
    STATUS current
    DESCRIPTION "Digital input 03 state. Station 11."
    ::= { sentiaLOKInput03States 111 }

sentiaLOKInput03State12 OBJECT-TYPE
    SYNTAX StrataonBinaryState
    MAX-ACCESS read-only
    STATUS current
    DESCRIPTION "Digital input 03 state. Station 12."
    ::= { sentiaLOKInput03States 112 }

sentiaLOKInput03State13 OBJECT-TYPE
    SYNTAX StrataonBinaryState
    MAX-ACCESS read-only
    STATUS current
    DESCRIPTION "Digital input 03 state. Station 13."
    ::= { sentiaLOKInput03States 113 }

sentiaLOKInput03State14 OBJECT-TYPE
    SYNTAX StrataonBinaryState
    MAX-ACCESS read-only
    STATUS current
    DESCRIPTION "Digital input 03 state. Station 14."
    ::= { sentiaLOKInput03States 114 }

sentiaLOKInput03State15 OBJECT-TYPE
    SYNTAX StrataonBinaryState
    MAX-ACCESS read-only
    STATUS current
    DESCRIPTION "Digital input 03 state. Station 15."
    ::= { sentiaLOKInput03States 115 }

sentiaLOKInput03State16 OBJECT-TYPE
    SYNTAX StrataonBinaryState
    MAX-ACCESS read-only
    STATUS current
    DESCRIPTION "Digital input 03 state. Station 16."
    ::= { sentiaLOKInput03States 116 }

sentiaLOKInput03State17 OBJECT-TYPE
    SYNTAX StrataonBinaryState
    MAX-ACCESS read-only
    STATUS current
    DESCRIPTION "Digital input 03 state. Station 17."
    ::= { sentiaLOKInput03States 117 }

sentiaLOKInput03State18 OBJECT-TYPE
    SYNTAX StrataonBinaryState
    MAX-ACCESS read-only
    STATUS current
    DESCRIPTION "Digital input 03 state. Station 18."
    ::= { sentiaLOKInput03States 118 }

sentiaLOKInput03State19 OBJECT-TYPE
    SYNTAX StrataonBinaryState
    MAX-ACCESS read-only
    STATUS current
    DESCRIPTION "Digital input 03 state. Station 19."
    ::= { sentiaLOKInput03States 119 }

sentiaLOKInput03State20 OBJECT-TYPE
    SYNTAX StrataonBinaryState
    MAX-ACCESS read-only
    STATUS current
    DESCRIPTION "Digital input 03 state. Station 20."
    ::= { sentiaLOKInput03States 120 }

sentiaLOKInput03State21 OBJECT-TYPE
    SYNTAX StrataonBinaryState
    MAX-ACCESS read-only
    STATUS current
    DESCRIPTION "Digital input 03 state. Station 21."
    ::= { sentiaLOKInput03States 121 }

sentiaLOKInput03State22 OBJECT-TYPE
    SYNTAX StrataonBinaryState
    MAX-ACCESS read-only
    STATUS current
    DESCRIPTION "Digital input 03 state. Station 22."
    ::= { sentiaLOKInput03States 122 }

sentiaLOKInput03State23 OBJECT-TYPE
    SYNTAX StrataonBinaryState
    MAX-ACCESS read-only
    STATUS current
    DESCRIPTION "Digital input 03 state. Station 23."
    ::= { sentiaLOKInput03States 123 }

sentiaLOKInput03State24 OBJECT-TYPE
    SYNTAX StrataonBinaryState
    MAX-ACCESS read-only
    STATUS current
    DESCRIPTION "Digital input 03 state. Station 24."
    ::= { sentiaLOKInput03States 124 }

sentiaLOKInput03State25 OBJECT-TYPE
    SYNTAX StrataonBinaryState
    MAX-ACCESS read-only
    STATUS current
    DESCRIPTION "Digital input 03 state. Station 25."
    ::= { sentiaLOKInput03States 125 }

sentiaLOKInput03State26 OBJECT-TYPE
    SYNTAX StrataonBinaryState
    MAX-ACCESS read-only
    STATUS current
    DESCRIPTION "Digital input 03 state. Station 26."
    ::= { sentiaLOKInput03States 126 }

sentiaLOKInput03State27 OBJECT-TYPE
    SYNTAX StrataonBinaryState
    MAX-ACCESS read-only
    STATUS current
    DESCRIPTION "Digital input 03 state. Station 27."
    ::= { sentiaLOKInput03States 127 }

sentiaLOKInput03State28 OBJECT-TYPE
    SYNTAX StrataonBinaryState
    MAX-ACCESS read-only
    STATUS current
    DESCRIPTION "Digital input 03 state. Station 28."
    ::= { sentiaLOKInput03States 128 }

sentiaLOKInput03State29 OBJECT-TYPE
    SYNTAX StrataonBinaryState
    MAX-ACCESS read-only
    STATUS current
    DESCRIPTION "Digital input 03 state. Station 29."
    ::= { sentiaLOKInput03States 129 }

sentiaLOKInput03State30 OBJECT-TYPE
    SYNTAX StrataonBinaryState
    MAX-ACCESS read-only
    STATUS current
    DESCRIPTION "Digital input 03 state. Station 30."
    ::= { sentiaLOKInput03States 130 }

sentiaLOKInput03State31 OBJECT-TYPE
    SYNTAX StrataonBinaryState
    MAX-ACCESS read-only
    STATUS current
    DESCRIPTION "Digital input 03 state. Station 31."
    ::= { sentiaLOKInput03States 131 }

sentiaLOKInput03State32 OBJECT-TYPE
    SYNTAX StrataonBinaryState
    MAX-ACCESS read-only
    STATUS current
    DESCRIPTION "Digital input 03 state. Station 32."
    ::= { sentiaLOKInput03States 132 }

sentiaLOKInput04States OBJECT-IDENTITY
    STATUS current
    DESCRIPTION "sentiaLOK digital input 04 state for stations 01..32; subidentifiers 101..132."
    ::= { strataonSentiaLOK 10 }

sentiaLOKInput04State01 OBJECT-TYPE
    SYNTAX StrataonBinaryState
    MAX-ACCESS read-only
    STATUS current
    DESCRIPTION "Digital input 04 state. Station 01."
    ::= { sentiaLOKInput04States 101 }

sentiaLOKInput04State02 OBJECT-TYPE
    SYNTAX StrataonBinaryState
    MAX-ACCESS read-only
    STATUS current
    DESCRIPTION "Digital input 04 state. Station 02."
    ::= { sentiaLOKInput04States 102 }

sentiaLOKInput04State03 OBJECT-TYPE
    SYNTAX StrataonBinaryState
    MAX-ACCESS read-only
    STATUS current
    DESCRIPTION "Digital input 04 state. Station 03."
    ::= { sentiaLOKInput04States 103 }

sentiaLOKInput04State04 OBJECT-TYPE
    SYNTAX StrataonBinaryState
    MAX-ACCESS read-only
    STATUS current
    DESCRIPTION "Digital input 04 state. Station 04."
    ::= { sentiaLOKInput04States 104 }

sentiaLOKInput04State05 OBJECT-TYPE
    SYNTAX StrataonBinaryState
    MAX-ACCESS read-only
    STATUS current
    DESCRIPTION "Digital input 04 state. Station 05."
    ::= { sentiaLOKInput04States 105 }

sentiaLOKInput04State06 OBJECT-TYPE
    SYNTAX StrataonBinaryState
    MAX-ACCESS read-only
    STATUS current
    DESCRIPTION "Digital input 04 state. Station 06."
    ::= { sentiaLOKInput04States 106 }

sentiaLOKInput04State07 OBJECT-TYPE
    SYNTAX StrataonBinaryState
    MAX-ACCESS read-only
    STATUS current
    DESCRIPTION "Digital input 04 state. Station 07."
    ::= { sentiaLOKInput04States 107 }

sentiaLOKInput04State08 OBJECT-TYPE
    SYNTAX StrataonBinaryState
    MAX-ACCESS read-only
    STATUS current
    DESCRIPTION "Digital input 04 state. Station 08."
    ::= { sentiaLOKInput04States 108 }

sentiaLOKInput04State09 OBJECT-TYPE
    SYNTAX StrataonBinaryState
    MAX-ACCESS read-only
    STATUS current
    DESCRIPTION "Digital input 04 state. Station 09."
    ::= { sentiaLOKInput04States 109 }

sentiaLOKInput04State10 OBJECT-TYPE
    SYNTAX StrataonBinaryState
    MAX-ACCESS read-only
    STATUS current
    DESCRIPTION "Digital input 04 state. Station 10."
    ::= { sentiaLOKInput04States 110 }

sentiaLOKInput04State11 OBJECT-TYPE
    SYNTAX StrataonBinaryState
    MAX-ACCESS read-only
    STATUS current
    DESCRIPTION "Digital input 04 state. Station 11."
    ::= { sentiaLOKInput04States 111 }

sentiaLOKInput04State12 OBJECT-TYPE
    SYNTAX StrataonBinaryState
    MAX-ACCESS read-only
    STATUS current
    DESCRIPTION "Digital input 04 state. Station 12."
    ::= { sentiaLOKInput04States 112 }

sentiaLOKInput04State13 OBJECT-TYPE
    SYNTAX StrataonBinaryState
    MAX-ACCESS read-only
    STATUS current
    DESCRIPTION "Digital input 04 state. Station 13."
    ::= { sentiaLOKInput04States 113 }

sentiaLOKInput04State14 OBJECT-TYPE
    SYNTAX StrataonBinaryState
    MAX-ACCESS read-only
    STATUS current
    DESCRIPTION "Digital input 04 state. Station 14."
    ::= { sentiaLOKInput04States 114 }

sentiaLOKInput04State15 OBJECT-TYPE
    SYNTAX StrataonBinaryState
    MAX-ACCESS read-only
    STATUS current
    DESCRIPTION "Digital input 04 state. Station 15."
    ::= { sentiaLOKInput04States 115 }

sentiaLOKInput04State16 OBJECT-TYPE
    SYNTAX StrataonBinaryState
    MAX-ACCESS read-only
    STATUS current
    DESCRIPTION "Digital input 04 state. Station 16."
    ::= { sentiaLOKInput04States 116 }

sentiaLOKInput04State17 OBJECT-TYPE
    SYNTAX StrataonBinaryState
    MAX-ACCESS read-only
    STATUS current
    DESCRIPTION "Digital input 04 state. Station 17."
    ::= { sentiaLOKInput04States 117 }

sentiaLOKInput04State18 OBJECT-TYPE
    SYNTAX StrataonBinaryState
    MAX-ACCESS read-only
    STATUS current
    DESCRIPTION "Digital input 04 state. Station 18."
    ::= { sentiaLOKInput04States 118 }

sentiaLOKInput04State19 OBJECT-TYPE
    SYNTAX StrataonBinaryState
    MAX-ACCESS read-only
    STATUS current
    DESCRIPTION "Digital input 04 state. Station 19."
    ::= { sentiaLOKInput04States 119 }

sentiaLOKInput04State20 OBJECT-TYPE
    SYNTAX StrataonBinaryState
    MAX-ACCESS read-only
    STATUS current
    DESCRIPTION "Digital input 04 state. Station 20."
    ::= { sentiaLOKInput04States 120 }

sentiaLOKInput04State21 OBJECT-TYPE
    SYNTAX StrataonBinaryState
    MAX-ACCESS read-only
    STATUS current
    DESCRIPTION "Digital input 04 state. Station 21."
    ::= { sentiaLOKInput04States 121 }

sentiaLOKInput04State22 OBJECT-TYPE
    SYNTAX StrataonBinaryState
    MAX-ACCESS read-only
    STATUS current
    DESCRIPTION "Digital input 04 state. Station 22."
    ::= { sentiaLOKInput04States 122 }

sentiaLOKInput04State23 OBJECT-TYPE
    SYNTAX StrataonBinaryState
    MAX-ACCESS read-only
    STATUS current
    DESCRIPTION "Digital input 04 state. Station 23."
    ::= { sentiaLOKInput04States 123 }

sentiaLOKInput04State24 OBJECT-TYPE
    SYNTAX StrataonBinaryState
    MAX-ACCESS read-only
    STATUS current
    DESCRIPTION "Digital input 04 state. Station 24."
    ::= { sentiaLOKInput04States 124 }

sentiaLOKInput04State25 OBJECT-TYPE
    SYNTAX StrataonBinaryState
    MAX-ACCESS read-only
    STATUS current
    DESCRIPTION "Digital input 04 state. Station 25."
    ::= { sentiaLOKInput04States 125 }

sentiaLOKInput04State26 OBJECT-TYPE
    SYNTAX StrataonBinaryState
    MAX-ACCESS read-only
    STATUS current
    DESCRIPTION "Digital input 04 state. Station 26."
    ::= { sentiaLOKInput04States 126 }

sentiaLOKInput04State27 OBJECT-TYPE
    SYNTAX StrataonBinaryState
    MAX-ACCESS read-only
    STATUS current
    DESCRIPTION "Digital input 04 state. Station 27."
    ::= { sentiaLOKInput04States 127 }

sentiaLOKInput04State28 OBJECT-TYPE
    SYNTAX StrataonBinaryState
    MAX-ACCESS read-only
    STATUS current
    DESCRIPTION "Digital input 04 state. Station 28."
    ::= { sentiaLOKInput04States 128 }

sentiaLOKInput04State29 OBJECT-TYPE
    SYNTAX StrataonBinaryState
    MAX-ACCESS read-only
    STATUS current
    DESCRIPTION "Digital input 04 state. Station 29."
    ::= { sentiaLOKInput04States 129 }

sentiaLOKInput04State30 OBJECT-TYPE
    SYNTAX StrataonBinaryState
    MAX-ACCESS read-only
    STATUS current
    DESCRIPTION "Digital input 04 state. Station 30."
    ::= { sentiaLOKInput04States 130 }

sentiaLOKInput04State31 OBJECT-TYPE
    SYNTAX StrataonBinaryState
    MAX-ACCESS read-only
    STATUS current
    DESCRIPTION "Digital input 04 state. Station 31."
    ::= { sentiaLOKInput04States 131 }

sentiaLOKInput04State32 OBJECT-TYPE
    SYNTAX StrataonBinaryState
    MAX-ACCESS read-only
    STATUS current
    DESCRIPTION "Digital input 04 state. Station 32."
    ::= { sentiaLOKInput04States 132 }

sentiaLOKInput05States OBJECT-IDENTITY
    STATUS current
    DESCRIPTION "sentiaLOK digital input 05 state for stations 01..32; subidentifiers 101..132."
    ::= { strataonSentiaLOK 11 }

sentiaLOKInput05State01 OBJECT-TYPE
    SYNTAX StrataonBinaryState
    MAX-ACCESS read-only
    STATUS current
    DESCRIPTION "Digital input 05 state. Station 01."
    ::= { sentiaLOKInput05States 101 }

sentiaLOKInput05State02 OBJECT-TYPE
    SYNTAX StrataonBinaryState
    MAX-ACCESS read-only
    STATUS current
    DESCRIPTION "Digital input 05 state. Station 02."
    ::= { sentiaLOKInput05States 102 }

sentiaLOKInput05State03 OBJECT-TYPE
    SYNTAX StrataonBinaryState
    MAX-ACCESS read-only
    STATUS current
    DESCRIPTION "Digital input 05 state. Station 03."
    ::= { sentiaLOKInput05States 103 }

sentiaLOKInput05State04 OBJECT-TYPE
    SYNTAX StrataonBinaryState
    MAX-ACCESS read-only
    STATUS current
    DESCRIPTION "Digital input 05 state. Station 04."
    ::= { sentiaLOKInput05States 104 }

sentiaLOKInput05State05 OBJECT-TYPE
    SYNTAX StrataonBinaryState
    MAX-ACCESS read-only
    STATUS current
    DESCRIPTION "Digital input 05 state. Station 05."
    ::= { sentiaLOKInput05States 105 }

sentiaLOKInput05State06 OBJECT-TYPE
    SYNTAX StrataonBinaryState
    MAX-ACCESS read-only
    STATUS current
    DESCRIPTION "Digital input 05 state. Station 06."
    ::= { sentiaLOKInput05States 106 }

sentiaLOKInput05State07 OBJECT-TYPE
    SYNTAX StrataonBinaryState
    MAX-ACCESS read-only
    STATUS current
    DESCRIPTION "Digital input 05 state. Station 07."
    ::= { sentiaLOKInput05States 107 }

sentiaLOKInput05State08 OBJECT-TYPE
    SYNTAX StrataonBinaryState
    MAX-ACCESS read-only
    STATUS current
    DESCRIPTION "Digital input 05 state. Station 08."
    ::= { sentiaLOKInput05States 108 }

sentiaLOKInput05State09 OBJECT-TYPE
    SYNTAX StrataonBinaryState
    MAX-ACCESS read-only
    STATUS current
    DESCRIPTION "Digital input 05 state. Station 09."
    ::= { sentiaLOKInput05States 109 }

sentiaLOKInput05State10 OBJECT-TYPE
    SYNTAX StrataonBinaryState
    MAX-ACCESS read-only
    STATUS current
    DESCRIPTION "Digital input 05 state. Station 10."
    ::= { sentiaLOKInput05States 110 }

sentiaLOKInput05State11 OBJECT-TYPE
    SYNTAX StrataonBinaryState
    MAX-ACCESS read-only
    STATUS current
    DESCRIPTION "Digital input 05 state. Station 11."
    ::= { sentiaLOKInput05States 111 }

sentiaLOKInput05State12 OBJECT-TYPE
    SYNTAX StrataonBinaryState
    MAX-ACCESS read-only
    STATUS current
    DESCRIPTION "Digital input 05 state. Station 12."
    ::= { sentiaLOKInput05States 112 }

sentiaLOKInput05State13 OBJECT-TYPE
    SYNTAX StrataonBinaryState
    MAX-ACCESS read-only
    STATUS current
    DESCRIPTION "Digital input 05 state. Station 13."
    ::= { sentiaLOKInput05States 113 }

sentiaLOKInput05State14 OBJECT-TYPE
    SYNTAX StrataonBinaryState
    MAX-ACCESS read-only
    STATUS current
    DESCRIPTION "Digital input 05 state. Station 14."
    ::= { sentiaLOKInput05States 114 }

sentiaLOKInput05State15 OBJECT-TYPE
    SYNTAX StrataonBinaryState
    MAX-ACCESS read-only
    STATUS current
    DESCRIPTION "Digital input 05 state. Station 15."
    ::= { sentiaLOKInput05States 115 }

sentiaLOKInput05State16 OBJECT-TYPE
    SYNTAX StrataonBinaryState
    MAX-ACCESS read-only
    STATUS current
    DESCRIPTION "Digital input 05 state. Station 16."
    ::= { sentiaLOKInput05States 116 }

sentiaLOKInput05State17 OBJECT-TYPE
    SYNTAX StrataonBinaryState
    MAX-ACCESS read-only
    STATUS current
    DESCRIPTION "Digital input 05 state. Station 17."
    ::= { sentiaLOKInput05States 117 }

sentiaLOKInput05State18 OBJECT-TYPE
    SYNTAX StrataonBinaryState
    MAX-ACCESS read-only
    STATUS current
    DESCRIPTION "Digital input 05 state. Station 18."
    ::= { sentiaLOKInput05States 118 }

sentiaLOKInput05State19 OBJECT-TYPE
    SYNTAX StrataonBinaryState
    MAX-ACCESS read-only
    STATUS current
    DESCRIPTION "Digital input 05 state. Station 19."
    ::= { sentiaLOKInput05States 119 }

sentiaLOKInput05State20 OBJECT-TYPE
    SYNTAX StrataonBinaryState
    MAX-ACCESS read-only
    STATUS current
    DESCRIPTION "Digital input 05 state. Station 20."
    ::= { sentiaLOKInput05States 120 }

sentiaLOKInput05State21 OBJECT-TYPE
    SYNTAX StrataonBinaryState
    MAX-ACCESS read-only
    STATUS current
    DESCRIPTION "Digital input 05 state. Station 21."
    ::= { sentiaLOKInput05States 121 }

sentiaLOKInput05State22 OBJECT-TYPE
    SYNTAX StrataonBinaryState
    MAX-ACCESS read-only
    STATUS current
    DESCRIPTION "Digital input 05 state. Station 22."
    ::= { sentiaLOKInput05States 122 }

sentiaLOKInput05State23 OBJECT-TYPE
    SYNTAX StrataonBinaryState
    MAX-ACCESS read-only
    STATUS current
    DESCRIPTION "Digital input 05 state. Station 23."
    ::= { sentiaLOKInput05States 123 }

sentiaLOKInput05State24 OBJECT-TYPE
    SYNTAX StrataonBinaryState
    MAX-ACCESS read-only
    STATUS current
    DESCRIPTION "Digital input 05 state. Station 24."
    ::= { sentiaLOKInput05States 124 }

sentiaLOKInput05State25 OBJECT-TYPE
    SYNTAX StrataonBinaryState
    MAX-ACCESS read-only
    STATUS current
    DESCRIPTION "Digital input 05 state. Station 25."
    ::= { sentiaLOKInput05States 125 }

sentiaLOKInput05State26 OBJECT-TYPE
    SYNTAX StrataonBinaryState
    MAX-ACCESS read-only
    STATUS current
    DESCRIPTION "Digital input 05 state. Station 26."
    ::= { sentiaLOKInput05States 126 }

sentiaLOKInput05State27 OBJECT-TYPE
    SYNTAX StrataonBinaryState
    MAX-ACCESS read-only
    STATUS current
    DESCRIPTION "Digital input 05 state. Station 27."
    ::= { sentiaLOKInput05States 127 }

sentiaLOKInput05State28 OBJECT-TYPE
    SYNTAX StrataonBinaryState
    MAX-ACCESS read-only
    STATUS current
    DESCRIPTION "Digital input 05 state. Station 28."
    ::= { sentiaLOKInput05States 128 }

sentiaLOKInput05State29 OBJECT-TYPE
    SYNTAX StrataonBinaryState
    MAX-ACCESS read-only
    STATUS current
    DESCRIPTION "Digital input 05 state. Station 29."
    ::= { sentiaLOKInput05States 129 }

sentiaLOKInput05State30 OBJECT-TYPE
    SYNTAX StrataonBinaryState
    MAX-ACCESS read-only
    STATUS current
    DESCRIPTION "Digital input 05 state. Station 30."
    ::= { sentiaLOKInput05States 130 }

sentiaLOKInput05State31 OBJECT-TYPE
    SYNTAX StrataonBinaryState
    MAX-ACCESS read-only
    STATUS current
    DESCRIPTION "Digital input 05 state. Station 31."
    ::= { sentiaLOKInput05States 131 }

sentiaLOKInput05State32 OBJECT-TYPE
    SYNTAX StrataonBinaryState
    MAX-ACCESS read-only
    STATUS current
    DESCRIPTION "Digital input 05 state. Station 32."
    ::= { sentiaLOKInput05States 132 }

sentiaLOKInput06States OBJECT-IDENTITY
    STATUS current
    DESCRIPTION "sentiaLOK digital input 06 state for stations 01..32; subidentifiers 101..132."
    ::= { strataonSentiaLOK 12 }

sentiaLOKInput06State01 OBJECT-TYPE
    SYNTAX StrataonBinaryState
    MAX-ACCESS read-only
    STATUS current
    DESCRIPTION "Digital input 06 state. Station 01."
    ::= { sentiaLOKInput06States 101 }

sentiaLOKInput06State02 OBJECT-TYPE
    SYNTAX StrataonBinaryState
    MAX-ACCESS read-only
    STATUS current
    DESCRIPTION "Digital input 06 state. Station 02."
    ::= { sentiaLOKInput06States 102 }

sentiaLOKInput06State03 OBJECT-TYPE
    SYNTAX StrataonBinaryState
    MAX-ACCESS read-only
    STATUS current
    DESCRIPTION "Digital input 06 state. Station 03."
    ::= { sentiaLOKInput06States 103 }

sentiaLOKInput06State04 OBJECT-TYPE
    SYNTAX StrataonBinaryState
    MAX-ACCESS read-only
    STATUS current
    DESCRIPTION "Digital input 06 state. Station 04."
    ::= { sentiaLOKInput06States 104 }

sentiaLOKInput06State05 OBJECT-TYPE
    SYNTAX StrataonBinaryState
    MAX-ACCESS read-only
    STATUS current
    DESCRIPTION "Digital input 06 state. Station 05."
    ::= { sentiaLOKInput06States 105 }

sentiaLOKInput06State06 OBJECT-TYPE
    SYNTAX StrataonBinaryState
    MAX-ACCESS read-only
    STATUS current
    DESCRIPTION "Digital input 06 state. Station 06."
    ::= { sentiaLOKInput06States 106 }

sentiaLOKInput06State07 OBJECT-TYPE
    SYNTAX StrataonBinaryState
    MAX-ACCESS read-only
    STATUS current
    DESCRIPTION "Digital input 06 state. Station 07."
    ::= { sentiaLOKInput06States 107 }

sentiaLOKInput06State08 OBJECT-TYPE
    SYNTAX StrataonBinaryState
    MAX-ACCESS read-only
    STATUS current
    DESCRIPTION "Digital input 06 state. Station 08."
    ::= { sentiaLOKInput06States 108 }

sentiaLOKInput06State09 OBJECT-TYPE
    SYNTAX StrataonBinaryState
    MAX-ACCESS read-only
    STATUS current
    DESCRIPTION "Digital input 06 state. Station 09."
    ::= { sentiaLOKInput06States 109 }

sentiaLOKInput06State10 OBJECT-TYPE
    SYNTAX StrataonBinaryState
    MAX-ACCESS read-only
    STATUS current
    DESCRIPTION "Digital input 06 state. Station 10."
    ::= { sentiaLOKInput06States 110 }

sentiaLOKInput06State11 OBJECT-TYPE
    SYNTAX StrataonBinaryState
    MAX-ACCESS read-only
    STATUS current
    DESCRIPTION "Digital input 06 state. Station 11."
    ::= { sentiaLOKInput06States 111 }

sentiaLOKInput06State12 OBJECT-TYPE
    SYNTAX StrataonBinaryState
    MAX-ACCESS read-only
    STATUS current
    DESCRIPTION "Digital input 06 state. Station 12."
    ::= { sentiaLOKInput06States 112 }

sentiaLOKInput06State13 OBJECT-TYPE
    SYNTAX StrataonBinaryState
    MAX-ACCESS read-only
    STATUS current
    DESCRIPTION "Digital input 06 state. Station 13."
    ::= { sentiaLOKInput06States 113 }

sentiaLOKInput06State14 OBJECT-TYPE
    SYNTAX StrataonBinaryState
    MAX-ACCESS read-only
    STATUS current
    DESCRIPTION "Digital input 06 state. Station 14."
    ::= { sentiaLOKInput06States 114 }

sentiaLOKInput06State15 OBJECT-TYPE
    SYNTAX StrataonBinaryState
    MAX-ACCESS read-only
    STATUS current
    DESCRIPTION "Digital input 06 state. Station 15."
    ::= { sentiaLOKInput06States 115 }

sentiaLOKInput06State16 OBJECT-TYPE
    SYNTAX StrataonBinaryState
    MAX-ACCESS read-only
    STATUS current
    DESCRIPTION "Digital input 06 state. Station 16."
    ::= { sentiaLOKInput06States 116 }

sentiaLOKInput06State17 OBJECT-TYPE
    SYNTAX StrataonBinaryState
    MAX-ACCESS read-only
    STATUS current
    DESCRIPTION "Digital input 06 state. Station 17."
    ::= { sentiaLOKInput06States 117 }

sentiaLOKInput06State18 OBJECT-TYPE
    SYNTAX StrataonBinaryState
    MAX-ACCESS read-only
    STATUS current
    DESCRIPTION "Digital input 06 state. Station 18."
    ::= { sentiaLOKInput06States 118 }

sentiaLOKInput06State19 OBJECT-TYPE
    SYNTAX StrataonBinaryState
    MAX-ACCESS read-only
    STATUS current
    DESCRIPTION "Digital input 06 state. Station 19."
    ::= { sentiaLOKInput06States 119 }

sentiaLOKInput06State20 OBJECT-TYPE
    SYNTAX StrataonBinaryState
    MAX-ACCESS read-only
    STATUS current
    DESCRIPTION "Digital input 06 state. Station 20."
    ::= { sentiaLOKInput06States 120 }

sentiaLOKInput06State21 OBJECT-TYPE
    SYNTAX StrataonBinaryState
    MAX-ACCESS read-only
    STATUS current
    DESCRIPTION "Digital input 06 state. Station 21."
    ::= { sentiaLOKInput06States 121 }

sentiaLOKInput06State22 OBJECT-TYPE
    SYNTAX StrataonBinaryState
    MAX-ACCESS read-only
    STATUS current
    DESCRIPTION "Digital input 06 state. Station 22."
    ::= { sentiaLOKInput06States 122 }

sentiaLOKInput06State23 OBJECT-TYPE
    SYNTAX StrataonBinaryState
    MAX-ACCESS read-only
    STATUS current
    DESCRIPTION "Digital input 06 state. Station 23."
    ::= { sentiaLOKInput06States 123 }

sentiaLOKInput06State24 OBJECT-TYPE
    SYNTAX StrataonBinaryState
    MAX-ACCESS read-only
    STATUS current
    DESCRIPTION "Digital input 06 state. Station 24."
    ::= { sentiaLOKInput06States 124 }

sentiaLOKInput06State25 OBJECT-TYPE
    SYNTAX StrataonBinaryState
    MAX-ACCESS read-only
    STATUS current
    DESCRIPTION "Digital input 06 state. Station 25."
    ::= { sentiaLOKInput06States 125 }

sentiaLOKInput06State26 OBJECT-TYPE
    SYNTAX StrataonBinaryState
    MAX-ACCESS read-only
    STATUS current
    DESCRIPTION "Digital input 06 state. Station 26."
    ::= { sentiaLOKInput06States 126 }

sentiaLOKInput06State27 OBJECT-TYPE
    SYNTAX StrataonBinaryState
    MAX-ACCESS read-only
    STATUS current
    DESCRIPTION "Digital input 06 state. Station 27."
    ::= { sentiaLOKInput06States 127 }

sentiaLOKInput06State28 OBJECT-TYPE
    SYNTAX StrataonBinaryState
    MAX-ACCESS read-only
    STATUS current
    DESCRIPTION "Digital input 06 state. Station 28."
    ::= { sentiaLOKInput06States 128 }

sentiaLOKInput06State29 OBJECT-TYPE
    SYNTAX StrataonBinaryState
    MAX-ACCESS read-only
    STATUS current
    DESCRIPTION "Digital input 06 state. Station 29."
    ::= { sentiaLOKInput06States 129 }

sentiaLOKInput06State30 OBJECT-TYPE
    SYNTAX StrataonBinaryState
    MAX-ACCESS read-only
    STATUS current
    DESCRIPTION "Digital input 06 state. Station 30."
    ::= { sentiaLOKInput06States 130 }

sentiaLOKInput06State31 OBJECT-TYPE
    SYNTAX StrataonBinaryState
    MAX-ACCESS read-only
    STATUS current
    DESCRIPTION "Digital input 06 state. Station 31."
    ::= { sentiaLOKInput06States 131 }

sentiaLOKInput06State32 OBJECT-TYPE
    SYNTAX StrataonBinaryState
    MAX-ACCESS read-only
    STATUS current
    DESCRIPTION "Digital input 06 state. Station 32."
    ::= { sentiaLOKInput06States 132 }

sentiaLOKInput07States OBJECT-IDENTITY
    STATUS current
    DESCRIPTION "sentiaLOK digital input 07 state for stations 01..32; subidentifiers 101..132."
    ::= { strataonSentiaLOK 13 }

sentiaLOKInput07State01 OBJECT-TYPE
    SYNTAX StrataonBinaryState
    MAX-ACCESS read-only
    STATUS current
    DESCRIPTION "Digital input 07 state. Station 01."
    ::= { sentiaLOKInput07States 101 }

sentiaLOKInput07State02 OBJECT-TYPE
    SYNTAX StrataonBinaryState
    MAX-ACCESS read-only
    STATUS current
    DESCRIPTION "Digital input 07 state. Station 02."
    ::= { sentiaLOKInput07States 102 }

sentiaLOKInput07State03 OBJECT-TYPE
    SYNTAX StrataonBinaryState
    MAX-ACCESS read-only
    STATUS current
    DESCRIPTION "Digital input 07 state. Station 03."
    ::= { sentiaLOKInput07States 103 }

sentiaLOKInput07State04 OBJECT-TYPE
    SYNTAX StrataonBinaryState
    MAX-ACCESS read-only
    STATUS current
    DESCRIPTION "Digital input 07 state. Station 04."
    ::= { sentiaLOKInput07States 104 }

sentiaLOKInput07State05 OBJECT-TYPE
    SYNTAX StrataonBinaryState
    MAX-ACCESS read-only
    STATUS current
    DESCRIPTION "Digital input 07 state. Station 05."
    ::= { sentiaLOKInput07States 105 }

sentiaLOKInput07State06 OBJECT-TYPE
    SYNTAX StrataonBinaryState
    MAX-ACCESS read-only
    STATUS current
    DESCRIPTION "Digital input 07 state. Station 06."
    ::= { sentiaLOKInput07States 106 }

sentiaLOKInput07State07 OBJECT-TYPE
    SYNTAX StrataonBinaryState
    MAX-ACCESS read-only
    STATUS current
    DESCRIPTION "Digital input 07 state. Station 07."
    ::= { sentiaLOKInput07States 107 }

sentiaLOKInput07State08 OBJECT-TYPE
    SYNTAX StrataonBinaryState
    MAX-ACCESS read-only
    STATUS current
    DESCRIPTION "Digital input 07 state. Station 08."
    ::= { sentiaLOKInput07States 108 }

sentiaLOKInput07State09 OBJECT-TYPE
    SYNTAX StrataonBinaryState
    MAX-ACCESS read-only
    STATUS current
    DESCRIPTION "Digital input 07 state. Station 09."
    ::= { sentiaLOKInput07States 109 }

sentiaLOKInput07State10 OBJECT-TYPE
    SYNTAX StrataonBinaryState
    MAX-ACCESS read-only
    STATUS current
    DESCRIPTION "Digital input 07 state. Station 10."
    ::= { sentiaLOKInput07States 110 }

sentiaLOKInput07State11 OBJECT-TYPE
    SYNTAX StrataonBinaryState
    MAX-ACCESS read-only
    STATUS current
    DESCRIPTION "Digital input 07 state. Station 11."
    ::= { sentiaLOKInput07States 111 }

sentiaLOKInput07State12 OBJECT-TYPE
    SYNTAX StrataonBinaryState
    MAX-ACCESS read-only
    STATUS current
    DESCRIPTION "Digital input 07 state. Station 12."
    ::= { sentiaLOKInput07States 112 }

sentiaLOKInput07State13 OBJECT-TYPE
    SYNTAX StrataonBinaryState
    MAX-ACCESS read-only
    STATUS current
    DESCRIPTION "Digital input 07 state. Station 13."
    ::= { sentiaLOKInput07States 113 }

sentiaLOKInput07State14 OBJECT-TYPE
    SYNTAX StrataonBinaryState
    MAX-ACCESS read-only
    STATUS current
    DESCRIPTION "Digital input 07 state. Station 14."
    ::= { sentiaLOKInput07States 114 }

sentiaLOKInput07State15 OBJECT-TYPE
    SYNTAX StrataonBinaryState
    MAX-ACCESS read-only
    STATUS current
    DESCRIPTION "Digital input 07 state. Station 15."
    ::= { sentiaLOKInput07States 115 }

sentiaLOKInput07State16 OBJECT-TYPE
    SYNTAX StrataonBinaryState
    MAX-ACCESS read-only
    STATUS current
    DESCRIPTION "Digital input 07 state. Station 16."
    ::= { sentiaLOKInput07States 116 }

sentiaLOKInput07State17 OBJECT-TYPE
    SYNTAX StrataonBinaryState
    MAX-ACCESS read-only
    STATUS current
    DESCRIPTION "Digital input 07 state. Station 17."
    ::= { sentiaLOKInput07States 117 }

sentiaLOKInput07State18 OBJECT-TYPE
    SYNTAX StrataonBinaryState
    MAX-ACCESS read-only
    STATUS current
    DESCRIPTION "Digital input 07 state. Station 18."
    ::= { sentiaLOKInput07States 118 }

sentiaLOKInput07State19 OBJECT-TYPE
    SYNTAX StrataonBinaryState
    MAX-ACCESS read-only
    STATUS current
    DESCRIPTION "Digital input 07 state. Station 19."
    ::= { sentiaLOKInput07States 119 }

sentiaLOKInput07State20 OBJECT-TYPE
    SYNTAX StrataonBinaryState
    MAX-ACCESS read-only
    STATUS current
    DESCRIPTION "Digital input 07 state. Station 20."
    ::= { sentiaLOKInput07States 120 }

sentiaLOKInput07State21 OBJECT-TYPE
    SYNTAX StrataonBinaryState
    MAX-ACCESS read-only
    STATUS current
    DESCRIPTION "Digital input 07 state. Station 21."
    ::= { sentiaLOKInput07States 121 }

sentiaLOKInput07State22 OBJECT-TYPE
    SYNTAX StrataonBinaryState
    MAX-ACCESS read-only
    STATUS current
    DESCRIPTION "Digital input 07 state. Station 22."
    ::= { sentiaLOKInput07States 122 }

sentiaLOKInput07State23 OBJECT-TYPE
    SYNTAX StrataonBinaryState
    MAX-ACCESS read-only
    STATUS current
    DESCRIPTION "Digital input 07 state. Station 23."
    ::= { sentiaLOKInput07States 123 }

sentiaLOKInput07State24 OBJECT-TYPE
    SYNTAX StrataonBinaryState
    MAX-ACCESS read-only
    STATUS current
    DESCRIPTION "Digital input 07 state. Station 24."
    ::= { sentiaLOKInput07States 124 }

sentiaLOKInput07State25 OBJECT-TYPE
    SYNTAX StrataonBinaryState
    MAX-ACCESS read-only
    STATUS current
    DESCRIPTION "Digital input 07 state. Station 25."
    ::= { sentiaLOKInput07States 125 }

sentiaLOKInput07State26 OBJECT-TYPE
    SYNTAX StrataonBinaryState
    MAX-ACCESS read-only
    STATUS current
    DESCRIPTION "Digital input 07 state. Station 26."
    ::= { sentiaLOKInput07States 126 }

sentiaLOKInput07State27 OBJECT-TYPE
    SYNTAX StrataonBinaryState
    MAX-ACCESS read-only
    STATUS current
    DESCRIPTION "Digital input 07 state. Station 27."
    ::= { sentiaLOKInput07States 127 }

sentiaLOKInput07State28 OBJECT-TYPE
    SYNTAX StrataonBinaryState
    MAX-ACCESS read-only
    STATUS current
    DESCRIPTION "Digital input 07 state. Station 28."
    ::= { sentiaLOKInput07States 128 }

sentiaLOKInput07State29 OBJECT-TYPE
    SYNTAX StrataonBinaryState
    MAX-ACCESS read-only
    STATUS current
    DESCRIPTION "Digital input 07 state. Station 29."
    ::= { sentiaLOKInput07States 129 }

sentiaLOKInput07State30 OBJECT-TYPE
    SYNTAX StrataonBinaryState
    MAX-ACCESS read-only
    STATUS current
    DESCRIPTION "Digital input 07 state. Station 30."
    ::= { sentiaLOKInput07States 130 }

sentiaLOKInput07State31 OBJECT-TYPE
    SYNTAX StrataonBinaryState
    MAX-ACCESS read-only
    STATUS current
    DESCRIPTION "Digital input 07 state. Station 31."
    ::= { sentiaLOKInput07States 131 }

sentiaLOKInput07State32 OBJECT-TYPE
    SYNTAX StrataonBinaryState
    MAX-ACCESS read-only
    STATUS current
    DESCRIPTION "Digital input 07 state. Station 32."
    ::= { sentiaLOKInput07States 132 }

sentiaLOKInput08States OBJECT-IDENTITY
    STATUS current
    DESCRIPTION "sentiaLOK digital input 08 state for stations 01..32; subidentifiers 101..132."
    ::= { strataonSentiaLOK 14 }

sentiaLOKInput08State01 OBJECT-TYPE
    SYNTAX StrataonBinaryState
    MAX-ACCESS read-only
    STATUS current
    DESCRIPTION "Digital input 08 state. Station 01."
    ::= { sentiaLOKInput08States 101 }

sentiaLOKInput08State02 OBJECT-TYPE
    SYNTAX StrataonBinaryState
    MAX-ACCESS read-only
    STATUS current
    DESCRIPTION "Digital input 08 state. Station 02."
    ::= { sentiaLOKInput08States 102 }

sentiaLOKInput08State03 OBJECT-TYPE
    SYNTAX StrataonBinaryState
    MAX-ACCESS read-only
    STATUS current
    DESCRIPTION "Digital input 08 state. Station 03."
    ::= { sentiaLOKInput08States 103 }

sentiaLOKInput08State04 OBJECT-TYPE
    SYNTAX StrataonBinaryState
    MAX-ACCESS read-only
    STATUS current
    DESCRIPTION "Digital input 08 state. Station 04."
    ::= { sentiaLOKInput08States 104 }

sentiaLOKInput08State05 OBJECT-TYPE
    SYNTAX StrataonBinaryState
    MAX-ACCESS read-only
    STATUS current
    DESCRIPTION "Digital input 08 state. Station 05."
    ::= { sentiaLOKInput08States 105 }

sentiaLOKInput08State06 OBJECT-TYPE
    SYNTAX StrataonBinaryState
    MAX-ACCESS read-only
    STATUS current
    DESCRIPTION "Digital input 08 state. Station 06."
    ::= { sentiaLOKInput08States 106 }

sentiaLOKInput08State07 OBJECT-TYPE
    SYNTAX StrataonBinaryState
    MAX-ACCESS read-only
    STATUS current
    DESCRIPTION "Digital input 08 state. Station 07."
    ::= { sentiaLOKInput08States 107 }

sentiaLOKInput08State08 OBJECT-TYPE
    SYNTAX StrataonBinaryState
    MAX-ACCESS read-only
    STATUS current
    DESCRIPTION "Digital input 08 state. Station 08."
    ::= { sentiaLOKInput08States 108 }

sentiaLOKInput08State09 OBJECT-TYPE
    SYNTAX StrataonBinaryState
    MAX-ACCESS read-only
    STATUS current
    DESCRIPTION "Digital input 08 state. Station 09."
    ::= { sentiaLOKInput08States 109 }

sentiaLOKInput08State10 OBJECT-TYPE
    SYNTAX StrataonBinaryState
    MAX-ACCESS read-only
    STATUS current
    DESCRIPTION "Digital input 08 state. Station 10."
    ::= { sentiaLOKInput08States 110 }

sentiaLOKInput08State11 OBJECT-TYPE
    SYNTAX StrataonBinaryState
    MAX-ACCESS read-only
    STATUS current
    DESCRIPTION "Digital input 08 state. Station 11."
    ::= { sentiaLOKInput08States 111 }

sentiaLOKInput08State12 OBJECT-TYPE
    SYNTAX StrataonBinaryState
    MAX-ACCESS read-only
    STATUS current
    DESCRIPTION "Digital input 08 state. Station 12."
    ::= { sentiaLOKInput08States 112 }

sentiaLOKInput08State13 OBJECT-TYPE
    SYNTAX StrataonBinaryState
    MAX-ACCESS read-only
    STATUS current
    DESCRIPTION "Digital input 08 state. Station 13."
    ::= { sentiaLOKInput08States 113 }

sentiaLOKInput08State14 OBJECT-TYPE
    SYNTAX StrataonBinaryState
    MAX-ACCESS read-only
    STATUS current
    DESCRIPTION "Digital input 08 state. Station 14."
    ::= { sentiaLOKInput08States 114 }

sentiaLOKInput08State15 OBJECT-TYPE
    SYNTAX StrataonBinaryState
    MAX-ACCESS read-only
    STATUS current
    DESCRIPTION "Digital input 08 state. Station 15."
    ::= { sentiaLOKInput08States 115 }

sentiaLOKInput08State16 OBJECT-TYPE
    SYNTAX StrataonBinaryState
    MAX-ACCESS read-only
    STATUS current
    DESCRIPTION "Digital input 08 state. Station 16."
    ::= { sentiaLOKInput08States 116 }

sentiaLOKInput08State17 OBJECT-TYPE
    SYNTAX StrataonBinaryState
    MAX-ACCESS read-only
    STATUS current
    DESCRIPTION "Digital input 08 state. Station 17."
    ::= { sentiaLOKInput08States 117 }

sentiaLOKInput08State18 OBJECT-TYPE
    SYNTAX StrataonBinaryState
    MAX-ACCESS read-only
    STATUS current
    DESCRIPTION "Digital input 08 state. Station 18."
    ::= { sentiaLOKInput08States 118 }

sentiaLOKInput08State19 OBJECT-TYPE
    SYNTAX StrataonBinaryState
    MAX-ACCESS read-only
    STATUS current
    DESCRIPTION "Digital input 08 state. Station 19."
    ::= { sentiaLOKInput08States 119 }

sentiaLOKInput08State20 OBJECT-TYPE
    SYNTAX StrataonBinaryState
    MAX-ACCESS read-only
    STATUS current
    DESCRIPTION "Digital input 08 state. Station 20."
    ::= { sentiaLOKInput08States 120 }

sentiaLOKInput08State21 OBJECT-TYPE
    SYNTAX StrataonBinaryState
    MAX-ACCESS read-only
    STATUS current
    DESCRIPTION "Digital input 08 state. Station 21."
    ::= { sentiaLOKInput08States 121 }

sentiaLOKInput08State22 OBJECT-TYPE
    SYNTAX StrataonBinaryState
    MAX-ACCESS read-only
    STATUS current
    DESCRIPTION "Digital input 08 state. Station 22."
    ::= { sentiaLOKInput08States 122 }

sentiaLOKInput08State23 OBJECT-TYPE
    SYNTAX StrataonBinaryState
    MAX-ACCESS read-only
    STATUS current
    DESCRIPTION "Digital input 08 state. Station 23."
    ::= { sentiaLOKInput08States 123 }

sentiaLOKInput08State24 OBJECT-TYPE
    SYNTAX StrataonBinaryState
    MAX-ACCESS read-only
    STATUS current
    DESCRIPTION "Digital input 08 state. Station 24."
    ::= { sentiaLOKInput08States 124 }

sentiaLOKInput08State25 OBJECT-TYPE
    SYNTAX StrataonBinaryState
    MAX-ACCESS read-only
    STATUS current
    DESCRIPTION "Digital input 08 state. Station 25."
    ::= { sentiaLOKInput08States 125 }

sentiaLOKInput08State26 OBJECT-TYPE
    SYNTAX StrataonBinaryState
    MAX-ACCESS read-only
    STATUS current
    DESCRIPTION "Digital input 08 state. Station 26."
    ::= { sentiaLOKInput08States 126 }

sentiaLOKInput08State27 OBJECT-TYPE
    SYNTAX StrataonBinaryState
    MAX-ACCESS read-only
    STATUS current
    DESCRIPTION "Digital input 08 state. Station 27."
    ::= { sentiaLOKInput08States 127 }

sentiaLOKInput08State28 OBJECT-TYPE
    SYNTAX StrataonBinaryState
    MAX-ACCESS read-only
    STATUS current
    DESCRIPTION "Digital input 08 state. Station 28."
    ::= { sentiaLOKInput08States 128 }

sentiaLOKInput08State29 OBJECT-TYPE
    SYNTAX StrataonBinaryState
    MAX-ACCESS read-only
    STATUS current
    DESCRIPTION "Digital input 08 state. Station 29."
    ::= { sentiaLOKInput08States 129 }

sentiaLOKInput08State30 OBJECT-TYPE
    SYNTAX StrataonBinaryState
    MAX-ACCESS read-only
    STATUS current
    DESCRIPTION "Digital input 08 state. Station 30."
    ::= { sentiaLOKInput08States 130 }

sentiaLOKInput08State31 OBJECT-TYPE
    SYNTAX StrataonBinaryState
    MAX-ACCESS read-only
    STATUS current
    DESCRIPTION "Digital input 08 state. Station 31."
    ::= { sentiaLOKInput08States 131 }

sentiaLOKInput08State32 OBJECT-TYPE
    SYNTAX StrataonBinaryState
    MAX-ACCESS read-only
    STATUS current
    DESCRIPTION "Digital input 08 state. Station 32."
    ::= { sentiaLOKInput08States 132 }

sentiaLOKOutput01States OBJECT-IDENTITY
    STATUS current
    DESCRIPTION "sentiaLOK digital output 01 state for stations 01..32; subidentifiers 101..132."
    ::= { strataonSentiaLOK 15 }

sentiaLOKOutput01State01 OBJECT-TYPE
    SYNTAX StrataonBinaryState
    MAX-ACCESS read-only
    STATUS current
    DESCRIPTION "Digital output 01 state. Station 01."
    ::= { sentiaLOKOutput01States 101 }

sentiaLOKOutput01State02 OBJECT-TYPE
    SYNTAX StrataonBinaryState
    MAX-ACCESS read-only
    STATUS current
    DESCRIPTION "Digital output 01 state. Station 02."
    ::= { sentiaLOKOutput01States 102 }

sentiaLOKOutput01State03 OBJECT-TYPE
    SYNTAX StrataonBinaryState
    MAX-ACCESS read-only
    STATUS current
    DESCRIPTION "Digital output 01 state. Station 03."
    ::= { sentiaLOKOutput01States 103 }

sentiaLOKOutput01State04 OBJECT-TYPE
    SYNTAX StrataonBinaryState
    MAX-ACCESS read-only
    STATUS current
    DESCRIPTION "Digital output 01 state. Station 04."
    ::= { sentiaLOKOutput01States 104 }

sentiaLOKOutput01State05 OBJECT-TYPE
    SYNTAX StrataonBinaryState
    MAX-ACCESS read-only
    STATUS current
    DESCRIPTION "Digital output 01 state. Station 05."
    ::= { sentiaLOKOutput01States 105 }

sentiaLOKOutput01State06 OBJECT-TYPE
    SYNTAX StrataonBinaryState
    MAX-ACCESS read-only
    STATUS current
    DESCRIPTION "Digital output 01 state. Station 06."
    ::= { sentiaLOKOutput01States 106 }

sentiaLOKOutput01State07 OBJECT-TYPE
    SYNTAX StrataonBinaryState
    MAX-ACCESS read-only
    STATUS current
    DESCRIPTION "Digital output 01 state. Station 07."
    ::= { sentiaLOKOutput01States 107 }

sentiaLOKOutput01State08 OBJECT-TYPE
    SYNTAX StrataonBinaryState
    MAX-ACCESS read-only
    STATUS current
    DESCRIPTION "Digital output 01 state. Station 08."
    ::= { sentiaLOKOutput01States 108 }

sentiaLOKOutput01State09 OBJECT-TYPE
    SYNTAX StrataonBinaryState
    MAX-ACCESS read-only
    STATUS current
    DESCRIPTION "Digital output 01 state. Station 09."
    ::= { sentiaLOKOutput01States 109 }

sentiaLOKOutput01State10 OBJECT-TYPE
    SYNTAX StrataonBinaryState
    MAX-ACCESS read-only
    STATUS current
    DESCRIPTION "Digital output 01 state. Station 10."
    ::= { sentiaLOKOutput01States 110 }

sentiaLOKOutput01State11 OBJECT-TYPE
    SYNTAX StrataonBinaryState
    MAX-ACCESS read-only
    STATUS current
    DESCRIPTION "Digital output 01 state. Station 11."
    ::= { sentiaLOKOutput01States 111 }

sentiaLOKOutput01State12 OBJECT-TYPE
    SYNTAX StrataonBinaryState
    MAX-ACCESS read-only
    STATUS current
    DESCRIPTION "Digital output 01 state. Station 12."
    ::= { sentiaLOKOutput01States 112 }

sentiaLOKOutput01State13 OBJECT-TYPE
    SYNTAX StrataonBinaryState
    MAX-ACCESS read-only
    STATUS current
    DESCRIPTION "Digital output 01 state. Station 13."
    ::= { sentiaLOKOutput01States 113 }

sentiaLOKOutput01State14 OBJECT-TYPE
    SYNTAX StrataonBinaryState
    MAX-ACCESS read-only
    STATUS current
    DESCRIPTION "Digital output 01 state. Station 14."
    ::= { sentiaLOKOutput01States 114 }

sentiaLOKOutput01State15 OBJECT-TYPE
    SYNTAX StrataonBinaryState
    MAX-ACCESS read-only
    STATUS current
    DESCRIPTION "Digital output 01 state. Station 15."
    ::= { sentiaLOKOutput01States 115 }

sentiaLOKOutput01State16 OBJECT-TYPE
    SYNTAX StrataonBinaryState
    MAX-ACCESS read-only
    STATUS current
    DESCRIPTION "Digital output 01 state. Station 16."
    ::= { sentiaLOKOutput01States 116 }

sentiaLOKOutput01State17 OBJECT-TYPE
    SYNTAX StrataonBinaryState
    MAX-ACCESS read-only
    STATUS current
    DESCRIPTION "Digital output 01 state. Station 17."
    ::= { sentiaLOKOutput01States 117 }

sentiaLOKOutput01State18 OBJECT-TYPE
    SYNTAX StrataonBinaryState
    MAX-ACCESS read-only
    STATUS current
    DESCRIPTION "Digital output 01 state. Station 18."
    ::= { sentiaLOKOutput01States 118 }

sentiaLOKOutput01State19 OBJECT-TYPE
    SYNTAX StrataonBinaryState
    MAX-ACCESS read-only
    STATUS current
    DESCRIPTION "Digital output 01 state. Station 19."
    ::= { sentiaLOKOutput01States 119 }

sentiaLOKOutput01State20 OBJECT-TYPE
    SYNTAX StrataonBinaryState
    MAX-ACCESS read-only
    STATUS current
    DESCRIPTION "Digital output 01 state. Station 20."
    ::= { sentiaLOKOutput01States 120 }

sentiaLOKOutput01State21 OBJECT-TYPE
    SYNTAX StrataonBinaryState
    MAX-ACCESS read-only
    STATUS current
    DESCRIPTION "Digital output 01 state. Station 21."
    ::= { sentiaLOKOutput01States 121 }

sentiaLOKOutput01State22 OBJECT-TYPE
    SYNTAX StrataonBinaryState
    MAX-ACCESS read-only
    STATUS current
    DESCRIPTION "Digital output 01 state. Station 22."
    ::= { sentiaLOKOutput01States 122 }

sentiaLOKOutput01State23 OBJECT-TYPE
    SYNTAX StrataonBinaryState
    MAX-ACCESS read-only
    STATUS current
    DESCRIPTION "Digital output 01 state. Station 23."
    ::= { sentiaLOKOutput01States 123 }

sentiaLOKOutput01State24 OBJECT-TYPE
    SYNTAX StrataonBinaryState
    MAX-ACCESS read-only
    STATUS current
    DESCRIPTION "Digital output 01 state. Station 24."
    ::= { sentiaLOKOutput01States 124 }

sentiaLOKOutput01State25 OBJECT-TYPE
    SYNTAX StrataonBinaryState
    MAX-ACCESS read-only
    STATUS current
    DESCRIPTION "Digital output 01 state. Station 25."
    ::= { sentiaLOKOutput01States 125 }

sentiaLOKOutput01State26 OBJECT-TYPE
    SYNTAX StrataonBinaryState
    MAX-ACCESS read-only
    STATUS current
    DESCRIPTION "Digital output 01 state. Station 26."
    ::= { sentiaLOKOutput01States 126 }

sentiaLOKOutput01State27 OBJECT-TYPE
    SYNTAX StrataonBinaryState
    MAX-ACCESS read-only
    STATUS current
    DESCRIPTION "Digital output 01 state. Station 27."
    ::= { sentiaLOKOutput01States 127 }

sentiaLOKOutput01State28 OBJECT-TYPE
    SYNTAX StrataonBinaryState
    MAX-ACCESS read-only
    STATUS current
    DESCRIPTION "Digital output 01 state. Station 28."
    ::= { sentiaLOKOutput01States 128 }

sentiaLOKOutput01State29 OBJECT-TYPE
    SYNTAX StrataonBinaryState
    MAX-ACCESS read-only
    STATUS current
    DESCRIPTION "Digital output 01 state. Station 29."
    ::= { sentiaLOKOutput01States 129 }

sentiaLOKOutput01State30 OBJECT-TYPE
    SYNTAX StrataonBinaryState
    MAX-ACCESS read-only
    STATUS current
    DESCRIPTION "Digital output 01 state. Station 30."
    ::= { sentiaLOKOutput01States 130 }

sentiaLOKOutput01State31 OBJECT-TYPE
    SYNTAX StrataonBinaryState
    MAX-ACCESS read-only
    STATUS current
    DESCRIPTION "Digital output 01 state. Station 31."
    ::= { sentiaLOKOutput01States 131 }

sentiaLOKOutput01State32 OBJECT-TYPE
    SYNTAX StrataonBinaryState
    MAX-ACCESS read-only
    STATUS current
    DESCRIPTION "Digital output 01 state. Station 32."
    ::= { sentiaLOKOutput01States 132 }

sentiaLOKOutput02States OBJECT-IDENTITY
    STATUS current
    DESCRIPTION "sentiaLOK digital output 02 state for stations 01..32; subidentifiers 101..132."
    ::= { strataonSentiaLOK 16 }

sentiaLOKOutput02State01 OBJECT-TYPE
    SYNTAX StrataonBinaryState
    MAX-ACCESS read-only
    STATUS current
    DESCRIPTION "Digital output 02 state. Station 01."
    ::= { sentiaLOKOutput02States 101 }

sentiaLOKOutput02State02 OBJECT-TYPE
    SYNTAX StrataonBinaryState
    MAX-ACCESS read-only
    STATUS current
    DESCRIPTION "Digital output 02 state. Station 02."
    ::= { sentiaLOKOutput02States 102 }

sentiaLOKOutput02State03 OBJECT-TYPE
    SYNTAX StrataonBinaryState
    MAX-ACCESS read-only
    STATUS current
    DESCRIPTION "Digital output 02 state. Station 03."
    ::= { sentiaLOKOutput02States 103 }

sentiaLOKOutput02State04 OBJECT-TYPE
    SYNTAX StrataonBinaryState
    MAX-ACCESS read-only
    STATUS current
    DESCRIPTION "Digital output 02 state. Station 04."
    ::= { sentiaLOKOutput02States 104 }

sentiaLOKOutput02State05 OBJECT-TYPE
    SYNTAX StrataonBinaryState
    MAX-ACCESS read-only
    STATUS current
    DESCRIPTION "Digital output 02 state. Station 05."
    ::= { sentiaLOKOutput02States 105 }

sentiaLOKOutput02State06 OBJECT-TYPE
    SYNTAX StrataonBinaryState
    MAX-ACCESS read-only
    STATUS current
    DESCRIPTION "Digital output 02 state. Station 06."
    ::= { sentiaLOKOutput02States 106 }

sentiaLOKOutput02State07 OBJECT-TYPE
    SYNTAX StrataonBinaryState
    MAX-ACCESS read-only
    STATUS current
    DESCRIPTION "Digital output 02 state. Station 07."
    ::= { sentiaLOKOutput02States 107 }

sentiaLOKOutput02State08 OBJECT-TYPE
    SYNTAX StrataonBinaryState
    MAX-ACCESS read-only
    STATUS current
    DESCRIPTION "Digital output 02 state. Station 08."
    ::= { sentiaLOKOutput02States 108 }

sentiaLOKOutput02State09 OBJECT-TYPE
    SYNTAX StrataonBinaryState
    MAX-ACCESS read-only
    STATUS current
    DESCRIPTION "Digital output 02 state. Station 09."
    ::= { sentiaLOKOutput02States 109 }

sentiaLOKOutput02State10 OBJECT-TYPE
    SYNTAX StrataonBinaryState
    MAX-ACCESS read-only
    STATUS current
    DESCRIPTION "Digital output 02 state. Station 10."
    ::= { sentiaLOKOutput02States 110 }

sentiaLOKOutput02State11 OBJECT-TYPE
    SYNTAX StrataonBinaryState
    MAX-ACCESS read-only
    STATUS current
    DESCRIPTION "Digital output 02 state. Station 11."
    ::= { sentiaLOKOutput02States 111 }

sentiaLOKOutput02State12 OBJECT-TYPE
    SYNTAX StrataonBinaryState
    MAX-ACCESS read-only
    STATUS current
    DESCRIPTION "Digital output 02 state. Station 12."
    ::= { sentiaLOKOutput02States 112 }

sentiaLOKOutput02State13 OBJECT-TYPE
    SYNTAX StrataonBinaryState
    MAX-ACCESS read-only
    STATUS current
    DESCRIPTION "Digital output 02 state. Station 13."
    ::= { sentiaLOKOutput02States 113 }

sentiaLOKOutput02State14 OBJECT-TYPE
    SYNTAX StrataonBinaryState
    MAX-ACCESS read-only
    STATUS current
    DESCRIPTION "Digital output 02 state. Station 14."
    ::= { sentiaLOKOutput02States 114 }

sentiaLOKOutput02State15 OBJECT-TYPE
    SYNTAX StrataonBinaryState
    MAX-ACCESS read-only
    STATUS current
    DESCRIPTION "Digital output 02 state. Station 15."
    ::= { sentiaLOKOutput02States 115 }

sentiaLOKOutput02State16 OBJECT-TYPE
    SYNTAX StrataonBinaryState
    MAX-ACCESS read-only
    STATUS current
    DESCRIPTION "Digital output 02 state. Station 16."
    ::= { sentiaLOKOutput02States 116 }

sentiaLOKOutput02State17 OBJECT-TYPE
    SYNTAX StrataonBinaryState
    MAX-ACCESS read-only
    STATUS current
    DESCRIPTION "Digital output 02 state. Station 17."
    ::= { sentiaLOKOutput02States 117 }

sentiaLOKOutput02State18 OBJECT-TYPE
    SYNTAX StrataonBinaryState
    MAX-ACCESS read-only
    STATUS current
    DESCRIPTION "Digital output 02 state. Station 18."
    ::= { sentiaLOKOutput02States 118 }

sentiaLOKOutput02State19 OBJECT-TYPE
    SYNTAX StrataonBinaryState
    MAX-ACCESS read-only
    STATUS current
    DESCRIPTION "Digital output 02 state. Station 19."
    ::= { sentiaLOKOutput02States 119 }

sentiaLOKOutput02State20 OBJECT-TYPE
    SYNTAX StrataonBinaryState
    MAX-ACCESS read-only
    STATUS current
    DESCRIPTION "Digital output 02 state. Station 20."
    ::= { sentiaLOKOutput02States 120 }

sentiaLOKOutput02State21 OBJECT-TYPE
    SYNTAX StrataonBinaryState
    MAX-ACCESS read-only
    STATUS current
    DESCRIPTION "Digital output 02 state. Station 21."
    ::= { sentiaLOKOutput02States 121 }

sentiaLOKOutput02State22 OBJECT-TYPE
    SYNTAX StrataonBinaryState
    MAX-ACCESS read-only
    STATUS current
    DESCRIPTION "Digital output 02 state. Station 22."
    ::= { sentiaLOKOutput02States 122 }

sentiaLOKOutput02State23 OBJECT-TYPE
    SYNTAX StrataonBinaryState
    MAX-ACCESS read-only
    STATUS current
    DESCRIPTION "Digital output 02 state. Station 23."
    ::= { sentiaLOKOutput02States 123 }

sentiaLOKOutput02State24 OBJECT-TYPE
    SYNTAX StrataonBinaryState
    MAX-ACCESS read-only
    STATUS current
    DESCRIPTION "Digital output 02 state. Station 24."
    ::= { sentiaLOKOutput02States 124 }

sentiaLOKOutput02State25 OBJECT-TYPE
    SYNTAX StrataonBinaryState
    MAX-ACCESS read-only
    STATUS current
    DESCRIPTION "Digital output 02 state. Station 25."
    ::= { sentiaLOKOutput02States 125 }

sentiaLOKOutput02State26 OBJECT-TYPE
    SYNTAX StrataonBinaryState
    MAX-ACCESS read-only
    STATUS current
    DESCRIPTION "Digital output 02 state. Station 26."
    ::= { sentiaLOKOutput02States 126 }

sentiaLOKOutput02State27 OBJECT-TYPE
    SYNTAX StrataonBinaryState
    MAX-ACCESS read-only
    STATUS current
    DESCRIPTION "Digital output 02 state. Station 27."
    ::= { sentiaLOKOutput02States 127 }

sentiaLOKOutput02State28 OBJECT-TYPE
    SYNTAX StrataonBinaryState
    MAX-ACCESS read-only
    STATUS current
    DESCRIPTION "Digital output 02 state. Station 28."
    ::= { sentiaLOKOutput02States 128 }

sentiaLOKOutput02State29 OBJECT-TYPE
    SYNTAX StrataonBinaryState
    MAX-ACCESS read-only
    STATUS current
    DESCRIPTION "Digital output 02 state. Station 29."
    ::= { sentiaLOKOutput02States 129 }

sentiaLOKOutput02State30 OBJECT-TYPE
    SYNTAX StrataonBinaryState
    MAX-ACCESS read-only
    STATUS current
    DESCRIPTION "Digital output 02 state. Station 30."
    ::= { sentiaLOKOutput02States 130 }

sentiaLOKOutput02State31 OBJECT-TYPE
    SYNTAX StrataonBinaryState
    MAX-ACCESS read-only
    STATUS current
    DESCRIPTION "Digital output 02 state. Station 31."
    ::= { sentiaLOKOutput02States 131 }

sentiaLOKOutput02State32 OBJECT-TYPE
    SYNTAX StrataonBinaryState
    MAX-ACCESS read-only
    STATUS current
    DESCRIPTION "Digital output 02 state. Station 32."
    ::= { sentiaLOKOutput02States 132 }

sentiaLOKOutput03States OBJECT-IDENTITY
    STATUS current
    DESCRIPTION "sentiaLOK digital output 03 state for stations 01..32; subidentifiers 101..132."
    ::= { strataonSentiaLOK 17 }

sentiaLOKOutput03State01 OBJECT-TYPE
    SYNTAX StrataonBinaryState
    MAX-ACCESS read-only
    STATUS current
    DESCRIPTION "Digital output 03 state. Station 01."
    ::= { sentiaLOKOutput03States 101 }

sentiaLOKOutput03State02 OBJECT-TYPE
    SYNTAX StrataonBinaryState
    MAX-ACCESS read-only
    STATUS current
    DESCRIPTION "Digital output 03 state. Station 02."
    ::= { sentiaLOKOutput03States 102 }

sentiaLOKOutput03State03 OBJECT-TYPE
    SYNTAX StrataonBinaryState
    MAX-ACCESS read-only
    STATUS current
    DESCRIPTION "Digital output 03 state. Station 03."
    ::= { sentiaLOKOutput03States 103 }

sentiaLOKOutput03State04 OBJECT-TYPE
    SYNTAX StrataonBinaryState
    MAX-ACCESS read-only
    STATUS current
    DESCRIPTION "Digital output 03 state. Station 04."
    ::= { sentiaLOKOutput03States 104 }

sentiaLOKOutput03State05 OBJECT-TYPE
    SYNTAX StrataonBinaryState
    MAX-ACCESS read-only
    STATUS current
    DESCRIPTION "Digital output 03 state. Station 05."
    ::= { sentiaLOKOutput03States 105 }

sentiaLOKOutput03State06 OBJECT-TYPE
    SYNTAX StrataonBinaryState
    MAX-ACCESS read-only
    STATUS current
    DESCRIPTION "Digital output 03 state. Station 06."
    ::= { sentiaLOKOutput03States 106 }

sentiaLOKOutput03State07 OBJECT-TYPE
    SYNTAX StrataonBinaryState
    MAX-ACCESS read-only
    STATUS current
    DESCRIPTION "Digital output 03 state. Station 07."
    ::= { sentiaLOKOutput03States 107 }

sentiaLOKOutput03State08 OBJECT-TYPE
    SYNTAX StrataonBinaryState
    MAX-ACCESS read-only
    STATUS current
    DESCRIPTION "Digital output 03 state. Station 08."
    ::= { sentiaLOKOutput03States 108 }

sentiaLOKOutput03State09 OBJECT-TYPE
    SYNTAX StrataonBinaryState
    MAX-ACCESS read-only
    STATUS current
    DESCRIPTION "Digital output 03 state. Station 09."
    ::= { sentiaLOKOutput03States 109 }

sentiaLOKOutput03State10 OBJECT-TYPE
    SYNTAX StrataonBinaryState
    MAX-ACCESS read-only
    STATUS current
    DESCRIPTION "Digital output 03 state. Station 10."
    ::= { sentiaLOKOutput03States 110 }

sentiaLOKOutput03State11 OBJECT-TYPE
    SYNTAX StrataonBinaryState
    MAX-ACCESS read-only
    STATUS current
    DESCRIPTION "Digital output 03 state. Station 11."
    ::= { sentiaLOKOutput03States 111 }

sentiaLOKOutput03State12 OBJECT-TYPE
    SYNTAX StrataonBinaryState
    MAX-ACCESS read-only
    STATUS current
    DESCRIPTION "Digital output 03 state. Station 12."
    ::= { sentiaLOKOutput03States 112 }

sentiaLOKOutput03State13 OBJECT-TYPE
    SYNTAX StrataonBinaryState
    MAX-ACCESS read-only
    STATUS current
    DESCRIPTION "Digital output 03 state. Station 13."
    ::= { sentiaLOKOutput03States 113 }

sentiaLOKOutput03State14 OBJECT-TYPE
    SYNTAX StrataonBinaryState
    MAX-ACCESS read-only
    STATUS current
    DESCRIPTION "Digital output 03 state. Station 14."
    ::= { sentiaLOKOutput03States 114 }

sentiaLOKOutput03State15 OBJECT-TYPE
    SYNTAX StrataonBinaryState
    MAX-ACCESS read-only
    STATUS current
    DESCRIPTION "Digital output 03 state. Station 15."
    ::= { sentiaLOKOutput03States 115 }

sentiaLOKOutput03State16 OBJECT-TYPE
    SYNTAX StrataonBinaryState
    MAX-ACCESS read-only
    STATUS current
    DESCRIPTION "Digital output 03 state. Station 16."
    ::= { sentiaLOKOutput03States 116 }

sentiaLOKOutput03State17 OBJECT-TYPE
    SYNTAX StrataonBinaryState
    MAX-ACCESS read-only
    STATUS current
    DESCRIPTION "Digital output 03 state. Station 17."
    ::= { sentiaLOKOutput03States 117 }

sentiaLOKOutput03State18 OBJECT-TYPE
    SYNTAX StrataonBinaryState
    MAX-ACCESS read-only
    STATUS current
    DESCRIPTION "Digital output 03 state. Station 18."
    ::= { sentiaLOKOutput03States 118 }

sentiaLOKOutput03State19 OBJECT-TYPE
    SYNTAX StrataonBinaryState
    MAX-ACCESS read-only
    STATUS current
    DESCRIPTION "Digital output 03 state. Station 19."
    ::= { sentiaLOKOutput03States 119 }

sentiaLOKOutput03State20 OBJECT-TYPE
    SYNTAX StrataonBinaryState
    MAX-ACCESS read-only
    STATUS current
    DESCRIPTION "Digital output 03 state. Station 20."
    ::= { sentiaLOKOutput03States 120 }

sentiaLOKOutput03State21 OBJECT-TYPE
    SYNTAX StrataonBinaryState
    MAX-ACCESS read-only
    STATUS current
    DESCRIPTION "Digital output 03 state. Station 21."
    ::= { sentiaLOKOutput03States 121 }

sentiaLOKOutput03State22 OBJECT-TYPE
    SYNTAX StrataonBinaryState
    MAX-ACCESS read-only
    STATUS current
    DESCRIPTION "Digital output 03 state. Station 22."
    ::= { sentiaLOKOutput03States 122 }

sentiaLOKOutput03State23 OBJECT-TYPE
    SYNTAX StrataonBinaryState
    MAX-ACCESS read-only
    STATUS current
    DESCRIPTION "Digital output 03 state. Station 23."
    ::= { sentiaLOKOutput03States 123 }

sentiaLOKOutput03State24 OBJECT-TYPE
    SYNTAX StrataonBinaryState
    MAX-ACCESS read-only
    STATUS current
    DESCRIPTION "Digital output 03 state. Station 24."
    ::= { sentiaLOKOutput03States 124 }

sentiaLOKOutput03State25 OBJECT-TYPE
    SYNTAX StrataonBinaryState
    MAX-ACCESS read-only
    STATUS current
    DESCRIPTION "Digital output 03 state. Station 25."
    ::= { sentiaLOKOutput03States 125 }

sentiaLOKOutput03State26 OBJECT-TYPE
    SYNTAX StrataonBinaryState
    MAX-ACCESS read-only
    STATUS current
    DESCRIPTION "Digital output 03 state. Station 26."
    ::= { sentiaLOKOutput03States 126 }

sentiaLOKOutput03State27 OBJECT-TYPE
    SYNTAX StrataonBinaryState
    MAX-ACCESS read-only
    STATUS current
    DESCRIPTION "Digital output 03 state. Station 27."
    ::= { sentiaLOKOutput03States 127 }

sentiaLOKOutput03State28 OBJECT-TYPE
    SYNTAX StrataonBinaryState
    MAX-ACCESS read-only
    STATUS current
    DESCRIPTION "Digital output 03 state. Station 28."
    ::= { sentiaLOKOutput03States 128 }

sentiaLOKOutput03State29 OBJECT-TYPE
    SYNTAX StrataonBinaryState
    MAX-ACCESS read-only
    STATUS current
    DESCRIPTION "Digital output 03 state. Station 29."
    ::= { sentiaLOKOutput03States 129 }

sentiaLOKOutput03State30 OBJECT-TYPE
    SYNTAX StrataonBinaryState
    MAX-ACCESS read-only
    STATUS current
    DESCRIPTION "Digital output 03 state. Station 30."
    ::= { sentiaLOKOutput03States 130 }

sentiaLOKOutput03State31 OBJECT-TYPE
    SYNTAX StrataonBinaryState
    MAX-ACCESS read-only
    STATUS current
    DESCRIPTION "Digital output 03 state. Station 31."
    ::= { sentiaLOKOutput03States 131 }

sentiaLOKOutput03State32 OBJECT-TYPE
    SYNTAX StrataonBinaryState
    MAX-ACCESS read-only
    STATUS current
    DESCRIPTION "Digital output 03 state. Station 32."
    ::= { sentiaLOKOutput03States 132 }

sentiaLOKOutput04States OBJECT-IDENTITY
    STATUS current
    DESCRIPTION "sentiaLOK digital output 04 state for stations 01..32; subidentifiers 101..132."
    ::= { strataonSentiaLOK 18 }

sentiaLOKOutput04State01 OBJECT-TYPE
    SYNTAX StrataonBinaryState
    MAX-ACCESS read-only
    STATUS current
    DESCRIPTION "Digital output 04 state. Station 01."
    ::= { sentiaLOKOutput04States 101 }

sentiaLOKOutput04State02 OBJECT-TYPE
    SYNTAX StrataonBinaryState
    MAX-ACCESS read-only
    STATUS current
    DESCRIPTION "Digital output 04 state. Station 02."
    ::= { sentiaLOKOutput04States 102 }

sentiaLOKOutput04State03 OBJECT-TYPE
    SYNTAX StrataonBinaryState
    MAX-ACCESS read-only
    STATUS current
    DESCRIPTION "Digital output 04 state. Station 03."
    ::= { sentiaLOKOutput04States 103 }

sentiaLOKOutput04State04 OBJECT-TYPE
    SYNTAX StrataonBinaryState
    MAX-ACCESS read-only
    STATUS current
    DESCRIPTION "Digital output 04 state. Station 04."
    ::= { sentiaLOKOutput04States 104 }

sentiaLOKOutput04State05 OBJECT-TYPE
    SYNTAX StrataonBinaryState
    MAX-ACCESS read-only
    STATUS current
    DESCRIPTION "Digital output 04 state. Station 05."
    ::= { sentiaLOKOutput04States 105 }

sentiaLOKOutput04State06 OBJECT-TYPE
    SYNTAX StrataonBinaryState
    MAX-ACCESS read-only
    STATUS current
    DESCRIPTION "Digital output 04 state. Station 06."
    ::= { sentiaLOKOutput04States 106 }

sentiaLOKOutput04State07 OBJECT-TYPE
    SYNTAX StrataonBinaryState
    MAX-ACCESS read-only
    STATUS current
    DESCRIPTION "Digital output 04 state. Station 07."
    ::= { sentiaLOKOutput04States 107 }

sentiaLOKOutput04State08 OBJECT-TYPE
    SYNTAX StrataonBinaryState
    MAX-ACCESS read-only
    STATUS current
    DESCRIPTION "Digital output 04 state. Station 08."
    ::= { sentiaLOKOutput04States 108 }

sentiaLOKOutput04State09 OBJECT-TYPE
    SYNTAX StrataonBinaryState
    MAX-ACCESS read-only
    STATUS current
    DESCRIPTION "Digital output 04 state. Station 09."
    ::= { sentiaLOKOutput04States 109 }

sentiaLOKOutput04State10 OBJECT-TYPE
    SYNTAX StrataonBinaryState
    MAX-ACCESS read-only
    STATUS current
    DESCRIPTION "Digital output 04 state. Station 10."
    ::= { sentiaLOKOutput04States 110 }

sentiaLOKOutput04State11 OBJECT-TYPE
    SYNTAX StrataonBinaryState
    MAX-ACCESS read-only
    STATUS current
    DESCRIPTION "Digital output 04 state. Station 11."
    ::= { sentiaLOKOutput04States 111 }

sentiaLOKOutput04State12 OBJECT-TYPE
    SYNTAX StrataonBinaryState
    MAX-ACCESS read-only
    STATUS current
    DESCRIPTION "Digital output 04 state. Station 12."
    ::= { sentiaLOKOutput04States 112 }

sentiaLOKOutput04State13 OBJECT-TYPE
    SYNTAX StrataonBinaryState
    MAX-ACCESS read-only
    STATUS current
    DESCRIPTION "Digital output 04 state. Station 13."
    ::= { sentiaLOKOutput04States 113 }

sentiaLOKOutput04State14 OBJECT-TYPE
    SYNTAX StrataonBinaryState
    MAX-ACCESS read-only
    STATUS current
    DESCRIPTION "Digital output 04 state. Station 14."
    ::= { sentiaLOKOutput04States 114 }

sentiaLOKOutput04State15 OBJECT-TYPE
    SYNTAX StrataonBinaryState
    MAX-ACCESS read-only
    STATUS current
    DESCRIPTION "Digital output 04 state. Station 15."
    ::= { sentiaLOKOutput04States 115 }

sentiaLOKOutput04State16 OBJECT-TYPE
    SYNTAX StrataonBinaryState
    MAX-ACCESS read-only
    STATUS current
    DESCRIPTION "Digital output 04 state. Station 16."
    ::= { sentiaLOKOutput04States 116 }

sentiaLOKOutput04State17 OBJECT-TYPE
    SYNTAX StrataonBinaryState
    MAX-ACCESS read-only
    STATUS current
    DESCRIPTION "Digital output 04 state. Station 17."
    ::= { sentiaLOKOutput04States 117 }

sentiaLOKOutput04State18 OBJECT-TYPE
    SYNTAX StrataonBinaryState
    MAX-ACCESS read-only
    STATUS current
    DESCRIPTION "Digital output 04 state. Station 18."
    ::= { sentiaLOKOutput04States 118 }

sentiaLOKOutput04State19 OBJECT-TYPE
    SYNTAX StrataonBinaryState
    MAX-ACCESS read-only
    STATUS current
    DESCRIPTION "Digital output 04 state. Station 19."
    ::= { sentiaLOKOutput04States 119 }

sentiaLOKOutput04State20 OBJECT-TYPE
    SYNTAX StrataonBinaryState
    MAX-ACCESS read-only
    STATUS current
    DESCRIPTION "Digital output 04 state. Station 20."
    ::= { sentiaLOKOutput04States 120 }

sentiaLOKOutput04State21 OBJECT-TYPE
    SYNTAX StrataonBinaryState
    MAX-ACCESS read-only
    STATUS current
    DESCRIPTION "Digital output 04 state. Station 21."
    ::= { sentiaLOKOutput04States 121 }

sentiaLOKOutput04State22 OBJECT-TYPE
    SYNTAX StrataonBinaryState
    MAX-ACCESS read-only
    STATUS current
    DESCRIPTION "Digital output 04 state. Station 22."
    ::= { sentiaLOKOutput04States 122 }

sentiaLOKOutput04State23 OBJECT-TYPE
    SYNTAX StrataonBinaryState
    MAX-ACCESS read-only
    STATUS current
    DESCRIPTION "Digital output 04 state. Station 23."
    ::= { sentiaLOKOutput04States 123 }

sentiaLOKOutput04State24 OBJECT-TYPE
    SYNTAX StrataonBinaryState
    MAX-ACCESS read-only
    STATUS current
    DESCRIPTION "Digital output 04 state. Station 24."
    ::= { sentiaLOKOutput04States 124 }

sentiaLOKOutput04State25 OBJECT-TYPE
    SYNTAX StrataonBinaryState
    MAX-ACCESS read-only
    STATUS current
    DESCRIPTION "Digital output 04 state. Station 25."
    ::= { sentiaLOKOutput04States 125 }

sentiaLOKOutput04State26 OBJECT-TYPE
    SYNTAX StrataonBinaryState
    MAX-ACCESS read-only
    STATUS current
    DESCRIPTION "Digital output 04 state. Station 26."
    ::= { sentiaLOKOutput04States 126 }

sentiaLOKOutput04State27 OBJECT-TYPE
    SYNTAX StrataonBinaryState
    MAX-ACCESS read-only
    STATUS current
    DESCRIPTION "Digital output 04 state. Station 27."
    ::= { sentiaLOKOutput04States 127 }

sentiaLOKOutput04State28 OBJECT-TYPE
    SYNTAX StrataonBinaryState
    MAX-ACCESS read-only
    STATUS current
    DESCRIPTION "Digital output 04 state. Station 28."
    ::= { sentiaLOKOutput04States 128 }

sentiaLOKOutput04State29 OBJECT-TYPE
    SYNTAX StrataonBinaryState
    MAX-ACCESS read-only
    STATUS current
    DESCRIPTION "Digital output 04 state. Station 29."
    ::= { sentiaLOKOutput04States 129 }

sentiaLOKOutput04State30 OBJECT-TYPE
    SYNTAX StrataonBinaryState
    MAX-ACCESS read-only
    STATUS current
    DESCRIPTION "Digital output 04 state. Station 30."
    ::= { sentiaLOKOutput04States 130 }

sentiaLOKOutput04State31 OBJECT-TYPE
    SYNTAX StrataonBinaryState
    MAX-ACCESS read-only
    STATUS current
    DESCRIPTION "Digital output 04 state. Station 31."
    ::= { sentiaLOKOutput04States 131 }

sentiaLOKOutput04State32 OBJECT-TYPE
    SYNTAX StrataonBinaryState
    MAX-ACCESS read-only
    STATUS current
    DESCRIPTION "Digital output 04 state. Station 32."
    ::= { sentiaLOKOutput04States 132 }

sentiaLOKOutput05States OBJECT-IDENTITY
    STATUS current
    DESCRIPTION "sentiaLOK digital output 05 state for stations 01..32; subidentifiers 101..132."
    ::= { strataonSentiaLOK 19 }

sentiaLOKOutput05State01 OBJECT-TYPE
    SYNTAX StrataonBinaryState
    MAX-ACCESS read-only
    STATUS current
    DESCRIPTION "Digital output 05 state. Station 01."
    ::= { sentiaLOKOutput05States 101 }

sentiaLOKOutput05State02 OBJECT-TYPE
    SYNTAX StrataonBinaryState
    MAX-ACCESS read-only
    STATUS current
    DESCRIPTION "Digital output 05 state. Station 02."
    ::= { sentiaLOKOutput05States 102 }

sentiaLOKOutput05State03 OBJECT-TYPE
    SYNTAX StrataonBinaryState
    MAX-ACCESS read-only
    STATUS current
    DESCRIPTION "Digital output 05 state. Station 03."
    ::= { sentiaLOKOutput05States 103 }

sentiaLOKOutput05State04 OBJECT-TYPE
    SYNTAX StrataonBinaryState
    MAX-ACCESS read-only
    STATUS current
    DESCRIPTION "Digital output 05 state. Station 04."
    ::= { sentiaLOKOutput05States 104 }

sentiaLOKOutput05State05 OBJECT-TYPE
    SYNTAX StrataonBinaryState
    MAX-ACCESS read-only
    STATUS current
    DESCRIPTION "Digital output 05 state. Station 05."
    ::= { sentiaLOKOutput05States 105 }

sentiaLOKOutput05State06 OBJECT-TYPE
    SYNTAX StrataonBinaryState
    MAX-ACCESS read-only
    STATUS current
    DESCRIPTION "Digital output 05 state. Station 06."
    ::= { sentiaLOKOutput05States 106 }

sentiaLOKOutput05State07 OBJECT-TYPE
    SYNTAX StrataonBinaryState
    MAX-ACCESS read-only
    STATUS current
    DESCRIPTION "Digital output 05 state. Station 07."
    ::= { sentiaLOKOutput05States 107 }

sentiaLOKOutput05State08 OBJECT-TYPE
    SYNTAX StrataonBinaryState
    MAX-ACCESS read-only
    STATUS current
    DESCRIPTION "Digital output 05 state. Station 08."
    ::= { sentiaLOKOutput05States 108 }

sentiaLOKOutput05State09 OBJECT-TYPE
    SYNTAX StrataonBinaryState
    MAX-ACCESS read-only
    STATUS current
    DESCRIPTION "Digital output 05 state. Station 09."
    ::= { sentiaLOKOutput05States 109 }

sentiaLOKOutput05State10 OBJECT-TYPE
    SYNTAX StrataonBinaryState
    MAX-ACCESS read-only
    STATUS current
    DESCRIPTION "Digital output 05 state. Station 10."
    ::= { sentiaLOKOutput05States 110 }

sentiaLOKOutput05State11 OBJECT-TYPE
    SYNTAX StrataonBinaryState
    MAX-ACCESS read-only
    STATUS current
    DESCRIPTION "Digital output 05 state. Station 11."
    ::= { sentiaLOKOutput05States 111 }

sentiaLOKOutput05State12 OBJECT-TYPE
    SYNTAX StrataonBinaryState
    MAX-ACCESS read-only
    STATUS current
    DESCRIPTION "Digital output 05 state. Station 12."
    ::= { sentiaLOKOutput05States 112 }

sentiaLOKOutput05State13 OBJECT-TYPE
    SYNTAX StrataonBinaryState
    MAX-ACCESS read-only
    STATUS current
    DESCRIPTION "Digital output 05 state. Station 13."
    ::= { sentiaLOKOutput05States 113 }

sentiaLOKOutput05State14 OBJECT-TYPE
    SYNTAX StrataonBinaryState
    MAX-ACCESS read-only
    STATUS current
    DESCRIPTION "Digital output 05 state. Station 14."
    ::= { sentiaLOKOutput05States 114 }

sentiaLOKOutput05State15 OBJECT-TYPE
    SYNTAX StrataonBinaryState
    MAX-ACCESS read-only
    STATUS current
    DESCRIPTION "Digital output 05 state. Station 15."
    ::= { sentiaLOKOutput05States 115 }

sentiaLOKOutput05State16 OBJECT-TYPE
    SYNTAX StrataonBinaryState
    MAX-ACCESS read-only
    STATUS current
    DESCRIPTION "Digital output 05 state. Station 16."
    ::= { sentiaLOKOutput05States 116 }

sentiaLOKOutput05State17 OBJECT-TYPE
    SYNTAX StrataonBinaryState
    MAX-ACCESS read-only
    STATUS current
    DESCRIPTION "Digital output 05 state. Station 17."
    ::= { sentiaLOKOutput05States 117 }

sentiaLOKOutput05State18 OBJECT-TYPE
    SYNTAX StrataonBinaryState
    MAX-ACCESS read-only
    STATUS current
    DESCRIPTION "Digital output 05 state. Station 18."
    ::= { sentiaLOKOutput05States 118 }

sentiaLOKOutput05State19 OBJECT-TYPE
    SYNTAX StrataonBinaryState
    MAX-ACCESS read-only
    STATUS current
    DESCRIPTION "Digital output 05 state. Station 19."
    ::= { sentiaLOKOutput05States 119 }

sentiaLOKOutput05State20 OBJECT-TYPE
    SYNTAX StrataonBinaryState
    MAX-ACCESS read-only
    STATUS current
    DESCRIPTION "Digital output 05 state. Station 20."
    ::= { sentiaLOKOutput05States 120 }

sentiaLOKOutput05State21 OBJECT-TYPE
    SYNTAX StrataonBinaryState
    MAX-ACCESS read-only
    STATUS current
    DESCRIPTION "Digital output 05 state. Station 21."
    ::= { sentiaLOKOutput05States 121 }

sentiaLOKOutput05State22 OBJECT-TYPE
    SYNTAX StrataonBinaryState
    MAX-ACCESS read-only
    STATUS current
    DESCRIPTION "Digital output 05 state. Station 22."
    ::= { sentiaLOKOutput05States 122 }

sentiaLOKOutput05State23 OBJECT-TYPE
    SYNTAX StrataonBinaryState
    MAX-ACCESS read-only
    STATUS current
    DESCRIPTION "Digital output 05 state. Station 23."
    ::= { sentiaLOKOutput05States 123 }

sentiaLOKOutput05State24 OBJECT-TYPE
    SYNTAX StrataonBinaryState
    MAX-ACCESS read-only
    STATUS current
    DESCRIPTION "Digital output 05 state. Station 24."
    ::= { sentiaLOKOutput05States 124 }

sentiaLOKOutput05State25 OBJECT-TYPE
    SYNTAX StrataonBinaryState
    MAX-ACCESS read-only
    STATUS current
    DESCRIPTION "Digital output 05 state. Station 25."
    ::= { sentiaLOKOutput05States 125 }

sentiaLOKOutput05State26 OBJECT-TYPE
    SYNTAX StrataonBinaryState
    MAX-ACCESS read-only
    STATUS current
    DESCRIPTION "Digital output 05 state. Station 26."
    ::= { sentiaLOKOutput05States 126 }

sentiaLOKOutput05State27 OBJECT-TYPE
    SYNTAX StrataonBinaryState
    MAX-ACCESS read-only
    STATUS current
    DESCRIPTION "Digital output 05 state. Station 27."
    ::= { sentiaLOKOutput05States 127 }

sentiaLOKOutput05State28 OBJECT-TYPE
    SYNTAX StrataonBinaryState
    MAX-ACCESS read-only
    STATUS current
    DESCRIPTION "Digital output 05 state. Station 28."
    ::= { sentiaLOKOutput05States 128 }

sentiaLOKOutput05State29 OBJECT-TYPE
    SYNTAX StrataonBinaryState
    MAX-ACCESS read-only
    STATUS current
    DESCRIPTION "Digital output 05 state. Station 29."
    ::= { sentiaLOKOutput05States 129 }

sentiaLOKOutput05State30 OBJECT-TYPE
    SYNTAX StrataonBinaryState
    MAX-ACCESS read-only
    STATUS current
    DESCRIPTION "Digital output 05 state. Station 30."
    ::= { sentiaLOKOutput05States 130 }

sentiaLOKOutput05State31 OBJECT-TYPE
    SYNTAX StrataonBinaryState
    MAX-ACCESS read-only
    STATUS current
    DESCRIPTION "Digital output 05 state. Station 31."
    ::= { sentiaLOKOutput05States 131 }

sentiaLOKOutput05State32 OBJECT-TYPE
    SYNTAX StrataonBinaryState
    MAX-ACCESS read-only
    STATUS current
    DESCRIPTION "Digital output 05 state. Station 32."
    ::= { sentiaLOKOutput05States 132 }

sentiaLOKOutput06States OBJECT-IDENTITY
    STATUS current
    DESCRIPTION "sentiaLOK digital output 06 state for stations 01..32; subidentifiers 101..132."
    ::= { strataonSentiaLOK 20 }

sentiaLOKOutput06State01 OBJECT-TYPE
    SYNTAX StrataonBinaryState
    MAX-ACCESS read-only
    STATUS current
    DESCRIPTION "Digital output 06 state. Station 01."
    ::= { sentiaLOKOutput06States 101 }

sentiaLOKOutput06State02 OBJECT-TYPE
    SYNTAX StrataonBinaryState
    MAX-ACCESS read-only
    STATUS current
    DESCRIPTION "Digital output 06 state. Station 02."
    ::= { sentiaLOKOutput06States 102 }

sentiaLOKOutput06State03 OBJECT-TYPE
    SYNTAX StrataonBinaryState
    MAX-ACCESS read-only
    STATUS current
    DESCRIPTION "Digital output 06 state. Station 03."
    ::= { sentiaLOKOutput06States 103 }

sentiaLOKOutput06State04 OBJECT-TYPE
    SYNTAX StrataonBinaryState
    MAX-ACCESS read-only
    STATUS current
    DESCRIPTION "Digital output 06 state. Station 04."
    ::= { sentiaLOKOutput06States 104 }

sentiaLOKOutput06State05 OBJECT-TYPE
    SYNTAX StrataonBinaryState
    MAX-ACCESS read-only
    STATUS current
    DESCRIPTION "Digital output 06 state. Station 05."
    ::= { sentiaLOKOutput06States 105 }

sentiaLOKOutput06State06 OBJECT-TYPE
    SYNTAX StrataonBinaryState
    MAX-ACCESS read-only
    STATUS current
    DESCRIPTION "Digital output 06 state. Station 06."
    ::= { sentiaLOKOutput06States 106 }

sentiaLOKOutput06State07 OBJECT-TYPE
    SYNTAX StrataonBinaryState
    MAX-ACCESS read-only
    STATUS current
    DESCRIPTION "Digital output 06 state. Station 07."
    ::= { sentiaLOKOutput06States 107 }

sentiaLOKOutput06State08 OBJECT-TYPE
    SYNTAX StrataonBinaryState
    MAX-ACCESS read-only
    STATUS current
    DESCRIPTION "Digital output 06 state. Station 08."
    ::= { sentiaLOKOutput06States 108 }

sentiaLOKOutput06State09 OBJECT-TYPE
    SYNTAX StrataonBinaryState
    MAX-ACCESS read-only
    STATUS current
    DESCRIPTION "Digital output 06 state. Station 09."
    ::= { sentiaLOKOutput06States 109 }

sentiaLOKOutput06State10 OBJECT-TYPE
    SYNTAX StrataonBinaryState
    MAX-ACCESS read-only
    STATUS current
    DESCRIPTION "Digital output 06 state. Station 10."
    ::= { sentiaLOKOutput06States 110 }

sentiaLOKOutput06State11 OBJECT-TYPE
    SYNTAX StrataonBinaryState
    MAX-ACCESS read-only
    STATUS current
    DESCRIPTION "Digital output 06 state. Station 11."
    ::= { sentiaLOKOutput06States 111 }

sentiaLOKOutput06State12 OBJECT-TYPE
    SYNTAX StrataonBinaryState
    MAX-ACCESS read-only
    STATUS current
    DESCRIPTION "Digital output 06 state. Station 12."
    ::= { sentiaLOKOutput06States 112 }

sentiaLOKOutput06State13 OBJECT-TYPE
    SYNTAX StrataonBinaryState
    MAX-ACCESS read-only
    STATUS current
    DESCRIPTION "Digital output 06 state. Station 13."
    ::= { sentiaLOKOutput06States 113 }

sentiaLOKOutput06State14 OBJECT-TYPE
    SYNTAX StrataonBinaryState
    MAX-ACCESS read-only
    STATUS current
    DESCRIPTION "Digital output 06 state. Station 14."
    ::= { sentiaLOKOutput06States 114 }

sentiaLOKOutput06State15 OBJECT-TYPE
    SYNTAX StrataonBinaryState
    MAX-ACCESS read-only
    STATUS current
    DESCRIPTION "Digital output 06 state. Station 15."
    ::= { sentiaLOKOutput06States 115 }

sentiaLOKOutput06State16 OBJECT-TYPE
    SYNTAX StrataonBinaryState
    MAX-ACCESS read-only
    STATUS current
    DESCRIPTION "Digital output 06 state. Station 16."
    ::= { sentiaLOKOutput06States 116 }

sentiaLOKOutput06State17 OBJECT-TYPE
    SYNTAX StrataonBinaryState
    MAX-ACCESS read-only
    STATUS current
    DESCRIPTION "Digital output 06 state. Station 17."
    ::= { sentiaLOKOutput06States 117 }

sentiaLOKOutput06State18 OBJECT-TYPE
    SYNTAX StrataonBinaryState
    MAX-ACCESS read-only
    STATUS current
    DESCRIPTION "Digital output 06 state. Station 18."
    ::= { sentiaLOKOutput06States 118 }

sentiaLOKOutput06State19 OBJECT-TYPE
    SYNTAX StrataonBinaryState
    MAX-ACCESS read-only
    STATUS current
    DESCRIPTION "Digital output 06 state. Station 19."
    ::= { sentiaLOKOutput06States 119 }

sentiaLOKOutput06State20 OBJECT-TYPE
    SYNTAX StrataonBinaryState
    MAX-ACCESS read-only
    STATUS current
    DESCRIPTION "Digital output 06 state. Station 20."
    ::= { sentiaLOKOutput06States 120 }

sentiaLOKOutput06State21 OBJECT-TYPE
    SYNTAX StrataonBinaryState
    MAX-ACCESS read-only
    STATUS current
    DESCRIPTION "Digital output 06 state. Station 21."
    ::= { sentiaLOKOutput06States 121 }

sentiaLOKOutput06State22 OBJECT-TYPE
    SYNTAX StrataonBinaryState
    MAX-ACCESS read-only
    STATUS current
    DESCRIPTION "Digital output 06 state. Station 22."
    ::= { sentiaLOKOutput06States 122 }

sentiaLOKOutput06State23 OBJECT-TYPE
    SYNTAX StrataonBinaryState
    MAX-ACCESS read-only
    STATUS current
    DESCRIPTION "Digital output 06 state. Station 23."
    ::= { sentiaLOKOutput06States 123 }

sentiaLOKOutput06State24 OBJECT-TYPE
    SYNTAX StrataonBinaryState
    MAX-ACCESS read-only
    STATUS current
    DESCRIPTION "Digital output 06 state. Station 24."
    ::= { sentiaLOKOutput06States 124 }

sentiaLOKOutput06State25 OBJECT-TYPE
    SYNTAX StrataonBinaryState
    MAX-ACCESS read-only
    STATUS current
    DESCRIPTION "Digital output 06 state. Station 25."
    ::= { sentiaLOKOutput06States 125 }

sentiaLOKOutput06State26 OBJECT-TYPE
    SYNTAX StrataonBinaryState
    MAX-ACCESS read-only
    STATUS current
    DESCRIPTION "Digital output 06 state. Station 26."
    ::= { sentiaLOKOutput06States 126 }

sentiaLOKOutput06State27 OBJECT-TYPE
    SYNTAX StrataonBinaryState
    MAX-ACCESS read-only
    STATUS current
    DESCRIPTION "Digital output 06 state. Station 27."
    ::= { sentiaLOKOutput06States 127 }

sentiaLOKOutput06State28 OBJECT-TYPE
    SYNTAX StrataonBinaryState
    MAX-ACCESS read-only
    STATUS current
    DESCRIPTION "Digital output 06 state. Station 28."
    ::= { sentiaLOKOutput06States 128 }

sentiaLOKOutput06State29 OBJECT-TYPE
    SYNTAX StrataonBinaryState
    MAX-ACCESS read-only
    STATUS current
    DESCRIPTION "Digital output 06 state. Station 29."
    ::= { sentiaLOKOutput06States 129 }

sentiaLOKOutput06State30 OBJECT-TYPE
    SYNTAX StrataonBinaryState
    MAX-ACCESS read-only
    STATUS current
    DESCRIPTION "Digital output 06 state. Station 30."
    ::= { sentiaLOKOutput06States 130 }

sentiaLOKOutput06State31 OBJECT-TYPE
    SYNTAX StrataonBinaryState
    MAX-ACCESS read-only
    STATUS current
    DESCRIPTION "Digital output 06 state. Station 31."
    ::= { sentiaLOKOutput06States 131 }

sentiaLOKOutput06State32 OBJECT-TYPE
    SYNTAX StrataonBinaryState
    MAX-ACCESS read-only
    STATUS current
    DESCRIPTION "Digital output 06 state. Station 32."
    ::= { sentiaLOKOutput06States 132 }

sentiaLOKOutput07States OBJECT-IDENTITY
    STATUS current
    DESCRIPTION "sentiaLOK digital output 07 state for stations 01..32; subidentifiers 101..132."
    ::= { strataonSentiaLOK 21 }

sentiaLOKOutput07State01 OBJECT-TYPE
    SYNTAX StrataonBinaryState
    MAX-ACCESS read-only
    STATUS current
    DESCRIPTION "Digital output 07 state. Station 01."
    ::= { sentiaLOKOutput07States 101 }

sentiaLOKOutput07State02 OBJECT-TYPE
    SYNTAX StrataonBinaryState
    MAX-ACCESS read-only
    STATUS current
    DESCRIPTION "Digital output 07 state. Station 02."
    ::= { sentiaLOKOutput07States 102 }

sentiaLOKOutput07State03 OBJECT-TYPE
    SYNTAX StrataonBinaryState
    MAX-ACCESS read-only
    STATUS current
    DESCRIPTION "Digital output 07 state. Station 03."
    ::= { sentiaLOKOutput07States 103 }

sentiaLOKOutput07State04 OBJECT-TYPE
    SYNTAX StrataonBinaryState
    MAX-ACCESS read-only
    STATUS current
    DESCRIPTION "Digital output 07 state. Station 04."
    ::= { sentiaLOKOutput07States 104 }

sentiaLOKOutput07State05 OBJECT-TYPE
    SYNTAX StrataonBinaryState
    MAX-ACCESS read-only
    STATUS current
    DESCRIPTION "Digital output 07 state. Station 05."
    ::= { sentiaLOKOutput07States 105 }

sentiaLOKOutput07State06 OBJECT-TYPE
    SYNTAX StrataonBinaryState
    MAX-ACCESS read-only
    STATUS current
    DESCRIPTION "Digital output 07 state. Station 06."
    ::= { sentiaLOKOutput07States 106 }

sentiaLOKOutput07State07 OBJECT-TYPE
    SYNTAX StrataonBinaryState
    MAX-ACCESS read-only
    STATUS current
    DESCRIPTION "Digital output 07 state. Station 07."
    ::= { sentiaLOKOutput07States 107 }

sentiaLOKOutput07State08 OBJECT-TYPE
    SYNTAX StrataonBinaryState
    MAX-ACCESS read-only
    STATUS current
    DESCRIPTION "Digital output 07 state. Station 08."
    ::= { sentiaLOKOutput07States 108 }

sentiaLOKOutput07State09 OBJECT-TYPE
    SYNTAX StrataonBinaryState
    MAX-ACCESS read-only
    STATUS current
    DESCRIPTION "Digital output 07 state. Station 09."
    ::= { sentiaLOKOutput07States 109 }

sentiaLOKOutput07State10 OBJECT-TYPE
    SYNTAX StrataonBinaryState
    MAX-ACCESS read-only
    STATUS current
    DESCRIPTION "Digital output 07 state. Station 10."
    ::= { sentiaLOKOutput07States 110 }

sentiaLOKOutput07State11 OBJECT-TYPE
    SYNTAX StrataonBinaryState
    MAX-ACCESS read-only
    STATUS current
    DESCRIPTION "Digital output 07 state. Station 11."
    ::= { sentiaLOKOutput07States 111 }

sentiaLOKOutput07State12 OBJECT-TYPE
    SYNTAX StrataonBinaryState
    MAX-ACCESS read-only
    STATUS current
    DESCRIPTION "Digital output 07 state. Station 12."
    ::= { sentiaLOKOutput07States 112 }

sentiaLOKOutput07State13 OBJECT-TYPE
    SYNTAX StrataonBinaryState
    MAX-ACCESS read-only
    STATUS current
    DESCRIPTION "Digital output 07 state. Station 13."
    ::= { sentiaLOKOutput07States 113 }

sentiaLOKOutput07State14 OBJECT-TYPE
    SYNTAX StrataonBinaryState
    MAX-ACCESS read-only
    STATUS current
    DESCRIPTION "Digital output 07 state. Station 14."
    ::= { sentiaLOKOutput07States 114 }

sentiaLOKOutput07State15 OBJECT-TYPE
    SYNTAX StrataonBinaryState
    MAX-ACCESS read-only
    STATUS current
    DESCRIPTION "Digital output 07 state. Station 15."
    ::= { sentiaLOKOutput07States 115 }

sentiaLOKOutput07State16 OBJECT-TYPE
    SYNTAX StrataonBinaryState
    MAX-ACCESS read-only
    STATUS current
    DESCRIPTION "Digital output 07 state. Station 16."
    ::= { sentiaLOKOutput07States 116 }

sentiaLOKOutput07State17 OBJECT-TYPE
    SYNTAX StrataonBinaryState
    MAX-ACCESS read-only
    STATUS current
    DESCRIPTION "Digital output 07 state. Station 17."
    ::= { sentiaLOKOutput07States 117 }

sentiaLOKOutput07State18 OBJECT-TYPE
    SYNTAX StrataonBinaryState
    MAX-ACCESS read-only
    STATUS current
    DESCRIPTION "Digital output 07 state. Station 18."
    ::= { sentiaLOKOutput07States 118 }

sentiaLOKOutput07State19 OBJECT-TYPE
    SYNTAX StrataonBinaryState
    MAX-ACCESS read-only
    STATUS current
    DESCRIPTION "Digital output 07 state. Station 19."
    ::= { sentiaLOKOutput07States 119 }

sentiaLOKOutput07State20 OBJECT-TYPE
    SYNTAX StrataonBinaryState
    MAX-ACCESS read-only
    STATUS current
    DESCRIPTION "Digital output 07 state. Station 20."
    ::= { sentiaLOKOutput07States 120 }

sentiaLOKOutput07State21 OBJECT-TYPE
    SYNTAX StrataonBinaryState
    MAX-ACCESS read-only
    STATUS current
    DESCRIPTION "Digital output 07 state. Station 21."
    ::= { sentiaLOKOutput07States 121 }

sentiaLOKOutput07State22 OBJECT-TYPE
    SYNTAX StrataonBinaryState
    MAX-ACCESS read-only
    STATUS current
    DESCRIPTION "Digital output 07 state. Station 22."
    ::= { sentiaLOKOutput07States 122 }

sentiaLOKOutput07State23 OBJECT-TYPE
    SYNTAX StrataonBinaryState
    MAX-ACCESS read-only
    STATUS current
    DESCRIPTION "Digital output 07 state. Station 23."
    ::= { sentiaLOKOutput07States 123 }

sentiaLOKOutput07State24 OBJECT-TYPE
    SYNTAX StrataonBinaryState
    MAX-ACCESS read-only
    STATUS current
    DESCRIPTION "Digital output 07 state. Station 24."
    ::= { sentiaLOKOutput07States 124 }

sentiaLOKOutput07State25 OBJECT-TYPE
    SYNTAX StrataonBinaryState
    MAX-ACCESS read-only
    STATUS current
    DESCRIPTION "Digital output 07 state. Station 25."
    ::= { sentiaLOKOutput07States 125 }

sentiaLOKOutput07State26 OBJECT-TYPE
    SYNTAX StrataonBinaryState
    MAX-ACCESS read-only
    STATUS current
    DESCRIPTION "Digital output 07 state. Station 26."
    ::= { sentiaLOKOutput07States 126 }

sentiaLOKOutput07State27 OBJECT-TYPE
    SYNTAX StrataonBinaryState
    MAX-ACCESS read-only
    STATUS current
    DESCRIPTION "Digital output 07 state. Station 27."
    ::= { sentiaLOKOutput07States 127 }

sentiaLOKOutput07State28 OBJECT-TYPE
    SYNTAX StrataonBinaryState
    MAX-ACCESS read-only
    STATUS current
    DESCRIPTION "Digital output 07 state. Station 28."
    ::= { sentiaLOKOutput07States 128 }

sentiaLOKOutput07State29 OBJECT-TYPE
    SYNTAX StrataonBinaryState
    MAX-ACCESS read-only
    STATUS current
    DESCRIPTION "Digital output 07 state. Station 29."
    ::= { sentiaLOKOutput07States 129 }

sentiaLOKOutput07State30 OBJECT-TYPE
    SYNTAX StrataonBinaryState
    MAX-ACCESS read-only
    STATUS current
    DESCRIPTION "Digital output 07 state. Station 30."
    ::= { sentiaLOKOutput07States 130 }

sentiaLOKOutput07State31 OBJECT-TYPE
    SYNTAX StrataonBinaryState
    MAX-ACCESS read-only
    STATUS current
    DESCRIPTION "Digital output 07 state. Station 31."
    ::= { sentiaLOKOutput07States 131 }

sentiaLOKOutput07State32 OBJECT-TYPE
    SYNTAX StrataonBinaryState
    MAX-ACCESS read-only
    STATUS current
    DESCRIPTION "Digital output 07 state. Station 32."
    ::= { sentiaLOKOutput07States 132 }

sentiaLOKOutput08States OBJECT-IDENTITY
    STATUS current
    DESCRIPTION "sentiaLOK digital output 08 state for stations 01..32; subidentifiers 101..132."
    ::= { strataonSentiaLOK 22 }

sentiaLOKOutput08State01 OBJECT-TYPE
    SYNTAX StrataonBinaryState
    MAX-ACCESS read-only
    STATUS current
    DESCRIPTION "Digital output 08 state. Station 01."
    ::= { sentiaLOKOutput08States 101 }

sentiaLOKOutput08State02 OBJECT-TYPE
    SYNTAX StrataonBinaryState
    MAX-ACCESS read-only
    STATUS current
    DESCRIPTION "Digital output 08 state. Station 02."
    ::= { sentiaLOKOutput08States 102 }

sentiaLOKOutput08State03 OBJECT-TYPE
    SYNTAX StrataonBinaryState
    MAX-ACCESS read-only
    STATUS current
    DESCRIPTION "Digital output 08 state. Station 03."
    ::= { sentiaLOKOutput08States 103 }

sentiaLOKOutput08State04 OBJECT-TYPE
    SYNTAX StrataonBinaryState
    MAX-ACCESS read-only
    STATUS current
    DESCRIPTION "Digital output 08 state. Station 04."
    ::= { sentiaLOKOutput08States 104 }

sentiaLOKOutput08State05 OBJECT-TYPE
    SYNTAX StrataonBinaryState
    MAX-ACCESS read-only
    STATUS current
    DESCRIPTION "Digital output 08 state. Station 05."
    ::= { sentiaLOKOutput08States 105 }

sentiaLOKOutput08State06 OBJECT-TYPE
    SYNTAX StrataonBinaryState
    MAX-ACCESS read-only
    STATUS current
    DESCRIPTION "Digital output 08 state. Station 06."
    ::= { sentiaLOKOutput08States 106 }

sentiaLOKOutput08State07 OBJECT-TYPE
    SYNTAX StrataonBinaryState
    MAX-ACCESS read-only
    STATUS current
    DESCRIPTION "Digital output 08 state. Station 07."
    ::= { sentiaLOKOutput08States 107 }

sentiaLOKOutput08State08 OBJECT-TYPE
    SYNTAX StrataonBinaryState
    MAX-ACCESS read-only
    STATUS current
    DESCRIPTION "Digital output 08 state. Station 08."
    ::= { sentiaLOKOutput08States 108 }

sentiaLOKOutput08State09 OBJECT-TYPE
    SYNTAX StrataonBinaryState
    MAX-ACCESS read-only
    STATUS current
    DESCRIPTION "Digital output 08 state. Station 09."
    ::= { sentiaLOKOutput08States 109 }

sentiaLOKOutput08State10 OBJECT-TYPE
    SYNTAX StrataonBinaryState
    MAX-ACCESS read-only
    STATUS current
    DESCRIPTION "Digital output 08 state. Station 10."
    ::= { sentiaLOKOutput08States 110 }

sentiaLOKOutput08State11 OBJECT-TYPE
    SYNTAX StrataonBinaryState
    MAX-ACCESS read-only
    STATUS current
    DESCRIPTION "Digital output 08 state. Station 11."
    ::= { sentiaLOKOutput08States 111 }

sentiaLOKOutput08State12 OBJECT-TYPE
    SYNTAX StrataonBinaryState
    MAX-ACCESS read-only
    STATUS current
    DESCRIPTION "Digital output 08 state. Station 12."
    ::= { sentiaLOKOutput08States 112 }

sentiaLOKOutput08State13 OBJECT-TYPE
    SYNTAX StrataonBinaryState
    MAX-ACCESS read-only
    STATUS current
    DESCRIPTION "Digital output 08 state. Station 13."
    ::= { sentiaLOKOutput08States 113 }

sentiaLOKOutput08State14 OBJECT-TYPE
    SYNTAX StrataonBinaryState
    MAX-ACCESS read-only
    STATUS current
    DESCRIPTION "Digital output 08 state. Station 14."
    ::= { sentiaLOKOutput08States 114 }

sentiaLOKOutput08State15 OBJECT-TYPE
    SYNTAX StrataonBinaryState
    MAX-ACCESS read-only
    STATUS current
    DESCRIPTION "Digital output 08 state. Station 15."
    ::= { sentiaLOKOutput08States 115 }

sentiaLOKOutput08State16 OBJECT-TYPE
    SYNTAX StrataonBinaryState
    MAX-ACCESS read-only
    STATUS current
    DESCRIPTION "Digital output 08 state. Station 16."
    ::= { sentiaLOKOutput08States 116 }

sentiaLOKOutput08State17 OBJECT-TYPE
    SYNTAX StrataonBinaryState
    MAX-ACCESS read-only
    STATUS current
    DESCRIPTION "Digital output 08 state. Station 17."
    ::= { sentiaLOKOutput08States 117 }

sentiaLOKOutput08State18 OBJECT-TYPE
    SYNTAX StrataonBinaryState
    MAX-ACCESS read-only
    STATUS current
    DESCRIPTION "Digital output 08 state. Station 18."
    ::= { sentiaLOKOutput08States 118 }

sentiaLOKOutput08State19 OBJECT-TYPE
    SYNTAX StrataonBinaryState
    MAX-ACCESS read-only
    STATUS current
    DESCRIPTION "Digital output 08 state. Station 19."
    ::= { sentiaLOKOutput08States 119 }

sentiaLOKOutput08State20 OBJECT-TYPE
    SYNTAX StrataonBinaryState
    MAX-ACCESS read-only
    STATUS current
    DESCRIPTION "Digital output 08 state. Station 20."
    ::= { sentiaLOKOutput08States 120 }

sentiaLOKOutput08State21 OBJECT-TYPE
    SYNTAX StrataonBinaryState
    MAX-ACCESS read-only
    STATUS current
    DESCRIPTION "Digital output 08 state. Station 21."
    ::= { sentiaLOKOutput08States 121 }

sentiaLOKOutput08State22 OBJECT-TYPE
    SYNTAX StrataonBinaryState
    MAX-ACCESS read-only
    STATUS current
    DESCRIPTION "Digital output 08 state. Station 22."
    ::= { sentiaLOKOutput08States 122 }

sentiaLOKOutput08State23 OBJECT-TYPE
    SYNTAX StrataonBinaryState
    MAX-ACCESS read-only
    STATUS current
    DESCRIPTION "Digital output 08 state. Station 23."
    ::= { sentiaLOKOutput08States 123 }

sentiaLOKOutput08State24 OBJECT-TYPE
    SYNTAX StrataonBinaryState
    MAX-ACCESS read-only
    STATUS current
    DESCRIPTION "Digital output 08 state. Station 24."
    ::= { sentiaLOKOutput08States 124 }

sentiaLOKOutput08State25 OBJECT-TYPE
    SYNTAX StrataonBinaryState
    MAX-ACCESS read-only
    STATUS current
    DESCRIPTION "Digital output 08 state. Station 25."
    ::= { sentiaLOKOutput08States 125 }

sentiaLOKOutput08State26 OBJECT-TYPE
    SYNTAX StrataonBinaryState
    MAX-ACCESS read-only
    STATUS current
    DESCRIPTION "Digital output 08 state. Station 26."
    ::= { sentiaLOKOutput08States 126 }

sentiaLOKOutput08State27 OBJECT-TYPE
    SYNTAX StrataonBinaryState
    MAX-ACCESS read-only
    STATUS current
    DESCRIPTION "Digital output 08 state. Station 27."
    ::= { sentiaLOKOutput08States 127 }

sentiaLOKOutput08State28 OBJECT-TYPE
    SYNTAX StrataonBinaryState
    MAX-ACCESS read-only
    STATUS current
    DESCRIPTION "Digital output 08 state. Station 28."
    ::= { sentiaLOKOutput08States 128 }

sentiaLOKOutput08State29 OBJECT-TYPE
    SYNTAX StrataonBinaryState
    MAX-ACCESS read-only
    STATUS current
    DESCRIPTION "Digital output 08 state. Station 29."
    ::= { sentiaLOKOutput08States 129 }

sentiaLOKOutput08State30 OBJECT-TYPE
    SYNTAX StrataonBinaryState
    MAX-ACCESS read-only
    STATUS current
    DESCRIPTION "Digital output 08 state. Station 30."
    ::= { sentiaLOKOutput08States 130 }

sentiaLOKOutput08State31 OBJECT-TYPE
    SYNTAX StrataonBinaryState
    MAX-ACCESS read-only
    STATUS current
    DESCRIPTION "Digital output 08 state. Station 31."
    ::= { sentiaLOKOutput08States 131 }

sentiaLOKOutput08State32 OBJECT-TYPE
    SYNTAX StrataonBinaryState
    MAX-ACCESS read-only
    STATUS current
    DESCRIPTION "Digital output 08 state. Station 32."
    ::= { sentiaLOKOutput08States 132 }

strataonCompliances OBJECT-IDENTITY
    STATUS current
    DESCRIPTION "Compliance statements."
    ::= { strataonConformance 1 }

strataonGroups OBJECT-IDENTITY
    STATUS current
    DESCRIPTION "Object groups."
    ::= { strataonConformance 2 }

strataonSystemGroup OBJECT-GROUP
    OBJECTS {
        strataonProductId,
        strataonUptime,
        strataonHeapFree,
        strataonHeapMinimum,
        strataonResetReason,
        strataonCpuFrequency,
        strataonModel,
        strataonSerialNumber,
        strataonFirmwareVersion,
        strataonBuildDate,
        strataonSdkVersion,
        strataonBuildTime
    }
    STATUS current
    DESCRIPTION
        "Common system objects implemented by STRATAON devices."
    ::= { strataonGroups 1 }

strataonNetworkGroup OBJECT-GROUP
    OBJECTS {
        strataonEthernetLink,
        strataonEthernetIp,
        strataonEthernetMask,
        strataonEthernetGateway,
        strataonEthernetMac,
        strataonWifiLink,
        strataonWifiIp,
        strataonWifiMask,
        strataonWifiGateway,
        strataonWifiMac,
        strataonHostname
    }
    STATUS current
    DESCRIPTION
        "Common network objects implemented by STRATAON devices."
    ::= { strataonGroups 2 }

strataonMiniPLCGroup OBJECT-GROUP
    OBJECTS {
        miniPLCDigitalInputCount,
        miniPLCDigitalOutputCount,
        miniPLCBooleanVariableCount,
        miniPLCLongVariableCount,
        miniPLCDI01,
        miniPLCDI02,
        miniPLCDI03,
        miniPLCDI04,
        miniPLCDI05,
        miniPLCDI06,
        miniPLCDI07,
        miniPLCDI08,
        miniPLCDI09,
        miniPLCDI10,
        miniPLCDI11,
        miniPLCDI12,
        miniPLCDI13,
        miniPLCDI14,
        miniPLCDI15,
        miniPLCDI16,
        miniPLCDI17,
        miniPLCDI18,
        miniPLCDI19,
        miniPLCDI20,
        miniPLCDI21,
        miniPLCDI22,
        miniPLCDI23,
        miniPLCDI24,
        miniPLCDI25,
        miniPLCDI26,
        miniPLCDI27,
        miniPLCDI28,
        miniPLCDI29,
        miniPLCDI30,
        miniPLCDI31,
        miniPLCDI32,
        miniPLCDO01,
        miniPLCDO02,
        miniPLCDO03,
        miniPLCDO04,
        miniPLCDO05,
        miniPLCDO06,
        miniPLCDO07,
        miniPLCDO08,
        miniPLCDO09,
        miniPLCDO10,
        miniPLCDO11,
        miniPLCDO12,
        miniPLCDO13,
        miniPLCDO14,
        miniPLCDO15,
        miniPLCDO16,
        miniPLCDO17,
        miniPLCDO18,
        miniPLCDO19,
        miniPLCDO20,
        miniPLCDO21,
        miniPLCDO22,
        miniPLCDO23,
        miniPLCDO24,
        miniPLCDO25,
        miniPLCDO26,
        miniPLCDO27,
        miniPLCDO28,
        miniPLCDO29,
        miniPLCDO30,
        miniPLCDO31,
        miniPLCDO32,
        miniPLCBOOL01,
        miniPLCBOOL02,
        miniPLCBOOL03,
        miniPLCBOOL04,
        miniPLCBOOL05,
        miniPLCBOOL06,
        miniPLCBOOL07,
        miniPLCBOOL08,
        miniPLCBOOL09,
        miniPLCBOOL10,
        miniPLCBOOL11,
        miniPLCBOOL12,
        miniPLCBOOL13,
        miniPLCBOOL14,
        miniPLCBOOL15,
        miniPLCBOOL16,
        miniPLCBOOL17,
        miniPLCBOOL18,
        miniPLCBOOL19,
        miniPLCBOOL20,
        miniPLCBOOL21,
        miniPLCBOOL22,
        miniPLCBOOL23,
        miniPLCBOOL24,
        miniPLCBOOL25,
        miniPLCBOOL26,
        miniPLCBOOL27,
        miniPLCBOOL28,
        miniPLCBOOL29,
        miniPLCBOOL30,
        miniPLCBOOL31,
        miniPLCBOOL32,
        miniPLCLONG01,
        miniPLCLONG02,
        miniPLCLONG03,
        miniPLCLONG04,
        miniPLCLONG05,
        miniPLCLONG06,
        miniPLCLONG07,
        miniPLCLONG08,
        miniPLCLONG09,
        miniPLCLONG10,
        miniPLCLONG11,
        miniPLCLONG12,
        miniPLCLONG13,
        miniPLCLONG14,
        miniPLCLONG15,
        miniPLCLONG16,
        miniPLCLONG17,
        miniPLCLONG18,
        miniPLCLONG19,
        miniPLCLONG20,
        miniPLCLONG21,
        miniPLCLONG22,
        miniPLCLONG23,
        miniPLCLONG24,
        miniPLCLONG25,
        miniPLCLONG26,
        miniPLCLONG27,
        miniPLCLONG28,
        miniPLCLONG29,
        miniPLCLONG30,
        miniPLCLONG31,
        miniPLCLONG32
    }
    STATUS current
    DESCRIPTION
        "miniPLC product-specific objects."
    ::= { strataonGroups 3 }

strataonMiniENVGroup OBJECT-GROUP
    OBJECTS {
        miniENVDigitalInputCount,
        miniENVDigitalOutputCount,
        miniENVBooleanVariableCount,
        miniENVLongVariableCount,
        miniENVAnalogInputCount,
        miniENVDI01,
        miniENVDI02,
        miniENVDI03,
        miniENVDI04,
        miniENVDI05,
        miniENVDI06,
        miniENVDI07,
        miniENVDI08,
        miniENVDI09,
        miniENVDO01,
        miniENVDO02,
        miniENVBOOL01,
        miniENVBOOL02,
        miniENVBOOL03,
        miniENVBOOL04,
        miniENVBOOL05,
        miniENVBOOL06,
        miniENVBOOL07,
        miniENVBOOL08,
        miniENVBOOL09,
        miniENVBOOL10,
        miniENVBOOL11,
        miniENVBOOL12,
        miniENVBOOL13,
        miniENVBOOL14,
        miniENVBOOL15,
        miniENVBOOL16,
        miniENVBOOL17,
        miniENVBOOL18,
        miniENVBOOL19,
        miniENVBOOL20,
        miniENVBOOL21,
        miniENVBOOL22,
        miniENVBOOL23,
        miniENVBOOL24,
        miniENVBOOL25,
        miniENVBOOL26,
        miniENVBOOL27,
        miniENVBOOL28,
        miniENVBOOL29,
        miniENVBOOL30,
        miniENVBOOL31,
        miniENVBOOL32,
        miniENVLONG01,
        miniENVLONG02,
        miniENVLONG03,
        miniENVLONG04,
        miniENVLONG05,
        miniENVLONG06,
        miniENVLONG07,
        miniENVLONG08,
        miniENVLONG09,
        miniENVLONG10,
        miniENVLONG11,
        miniENVLONG12,
        miniENVLONG13,
        miniENVLONG14,
        miniENVLONG15,
        miniENVLONG16,
        miniENVLONG17,
        miniENVLONG18,
        miniENVLONG19,
        miniENVLONG20,
        miniENVLONG21,
        miniENVLONG22,
        miniENVLONG23,
        miniENVLONG24,
        miniENVLONG25,
        miniENVLONG26,
        miniENVLONG27,
        miniENVLONG28,
        miniENVLONG29,
        miniENVLONG30,
        miniENVLONG31,
        miniENVLONG32,
        miniENVTEMP01,
        miniENVTEMP02,
        miniENVTEMP03,
        miniENVTEMP04,
        miniENVTEMP05,
        miniENVHUM01,
        miniENVHUM02,
        miniENVCO201
    }
    STATUS current
    DESCRIPTION
        "miniENV product-specific objects."
    ::= { strataonGroups 6 }

strataonSmartPDURelayGroup OBJECT-GROUP
    OBJECTS {
        smartPDURelayCount,
        smartPDURelay01,
        smartPDURelay02,
        smartPDURelay03,
        smartPDURelay04,
        smartPDURelay05,
        smartPDURelay06,
        smartPDURelay07,
        smartPDURelay08
    }
    STATUS current
    DESCRIPTION
        "smartPDU relay/outlet objects."
    ::= { strataonGroups 4 }

strataonPduRelayStatsGroup OBJECT-GROUP
    OBJECTS {
        smartPDURelayOnCount01,
        smartPDURelayOnCount02,
        smartPDURelayOnCount03,
        smartPDURelayOnCount04,
        smartPDURelayOnCount05,
        smartPDURelayOnCount06,
        smartPDURelayOnCount07,
        smartPDURelayOnCount08
    }
    STATUS current
    DESCRIPTION
        "Persistent smartPDU relay activation counter objects."
    ::= { strataonGroups 5 }

strataonSentiaMANGroup OBJECT-GROUP
    OBJECTS {
        sentiaMANStationCount,
        sentiaMANStationNode01,
        sentiaMANStationNode02,
        sentiaMANStationNode03,
        sentiaMANStationNode04,
        sentiaMANStationNode05,
        sentiaMANStationNode06,
        sentiaMANStationNode07,
        sentiaMANStationNode08,
        sentiaMANStationNode09,
        sentiaMANStationNode10,
        sentiaMANStationNode11,
        sentiaMANStationNode12,
        sentiaMANStationNode13,
        sentiaMANStationNode14,
        sentiaMANStationNode15,
        sentiaMANStationNode16,
        sentiaMANStationNode17,
        sentiaMANStationNode18,
        sentiaMANStationNode19,
        sentiaMANStationNode20,
        sentiaMANStationNode21,
        sentiaMANStationNode22,
        sentiaMANStationNode23,
        sentiaMANStationNode24,
        sentiaMANStationNode25,
        sentiaMANStationNode26,
        sentiaMANStationNode27,
        sentiaMANStationNode28,
        sentiaMANStationNode29,
        sentiaMANStationNode30,
        sentiaMANStationNode31,
        sentiaMANStationNode32,
        sentiaMANStationName01,
        sentiaMANStationName02,
        sentiaMANStationName03,
        sentiaMANStationName04,
        sentiaMANStationName05,
        sentiaMANStationName06,
        sentiaMANStationName07,
        sentiaMANStationName08,
        sentiaMANStationName09,
        sentiaMANStationName10,
        sentiaMANStationName11,
        sentiaMANStationName12,
        sentiaMANStationName13,
        sentiaMANStationName14,
        sentiaMANStationName15,
        sentiaMANStationName16,
        sentiaMANStationName17,
        sentiaMANStationName18,
        sentiaMANStationName19,
        sentiaMANStationName20,
        sentiaMANStationName21,
        sentiaMANStationName22,
        sentiaMANStationName23,
        sentiaMANStationName24,
        sentiaMANStationName25,
        sentiaMANStationName26,
        sentiaMANStationName27,
        sentiaMANStationName28,
        sentiaMANStationName29,
        sentiaMANStationName30,
        sentiaMANStationName31,
        sentiaMANStationName32,
        sentiaMANStationCommStatus01,
        sentiaMANStationCommStatus02,
        sentiaMANStationCommStatus03,
        sentiaMANStationCommStatus04,
        sentiaMANStationCommStatus05,
        sentiaMANStationCommStatus06,
        sentiaMANStationCommStatus07,
        sentiaMANStationCommStatus08,
        sentiaMANStationCommStatus09,
        sentiaMANStationCommStatus10,
        sentiaMANStationCommStatus11,
        sentiaMANStationCommStatus12,
        sentiaMANStationCommStatus13,
        sentiaMANStationCommStatus14,
        sentiaMANStationCommStatus15,
        sentiaMANStationCommStatus16,
        sentiaMANStationCommStatus17,
        sentiaMANStationCommStatus18,
        sentiaMANStationCommStatus19,
        sentiaMANStationCommStatus20,
        sentiaMANStationCommStatus21,
        sentiaMANStationCommStatus22,
        sentiaMANStationCommStatus23,
        sentiaMANStationCommStatus24,
        sentiaMANStationCommStatus25,
        sentiaMANStationCommStatus26,
        sentiaMANStationCommStatus27,
        sentiaMANStationCommStatus28,
        sentiaMANStationCommStatus29,
        sentiaMANStationCommStatus30,
        sentiaMANStationCommStatus31,
        sentiaMANStationCommStatus32,
        sentiaMANStationFirmware01,
        sentiaMANStationFirmware02,
        sentiaMANStationFirmware03,
        sentiaMANStationFirmware04,
        sentiaMANStationFirmware05,
        sentiaMANStationFirmware06,
        sentiaMANStationFirmware07,
        sentiaMANStationFirmware08,
        sentiaMANStationFirmware09,
        sentiaMANStationFirmware10,
        sentiaMANStationFirmware11,
        sentiaMANStationFirmware12,
        sentiaMANStationFirmware13,
        sentiaMANStationFirmware14,
        sentiaMANStationFirmware15,
        sentiaMANStationFirmware16,
        sentiaMANStationFirmware17,
        sentiaMANStationFirmware18,
        sentiaMANStationFirmware19,
        sentiaMANStationFirmware20,
        sentiaMANStationFirmware21,
        sentiaMANStationFirmware22,
        sentiaMANStationFirmware23,
        sentiaMANStationFirmware24,
        sentiaMANStationFirmware25,
        sentiaMANStationFirmware26,
        sentiaMANStationFirmware27,
        sentiaMANStationFirmware28,
        sentiaMANStationFirmware29,
        sentiaMANStationFirmware30,
        sentiaMANStationFirmware31,
        sentiaMANStationFirmware32,
        sentiaMANStationTemp101,
        sentiaMANStationTemp102,
        sentiaMANStationTemp103,
        sentiaMANStationTemp104,
        sentiaMANStationTemp105,
        sentiaMANStationTemp106,
        sentiaMANStationTemp107,
        sentiaMANStationTemp108,
        sentiaMANStationTemp109,
        sentiaMANStationTemp110,
        sentiaMANStationTemp111,
        sentiaMANStationTemp112,
        sentiaMANStationTemp113,
        sentiaMANStationTemp114,
        sentiaMANStationTemp115,
        sentiaMANStationTemp116,
        sentiaMANStationTemp117,
        sentiaMANStationTemp118,
        sentiaMANStationTemp119,
        sentiaMANStationTemp120,
        sentiaMANStationTemp121,
        sentiaMANStationTemp122,
        sentiaMANStationTemp123,
        sentiaMANStationTemp124,
        sentiaMANStationTemp125,
        sentiaMANStationTemp126,
        sentiaMANStationTemp127,
        sentiaMANStationTemp128,
        sentiaMANStationTemp129,
        sentiaMANStationTemp130,
        sentiaMANStationTemp131,
        sentiaMANStationTemp132,
        sentiaMANStationTemp201,
        sentiaMANStationTemp202,
        sentiaMANStationTemp203,
        sentiaMANStationTemp204,
        sentiaMANStationTemp205,
        sentiaMANStationTemp206,
        sentiaMANStationTemp207,
        sentiaMANStationTemp208,
        sentiaMANStationTemp209,
        sentiaMANStationTemp210,
        sentiaMANStationTemp211,
        sentiaMANStationTemp212,
        sentiaMANStationTemp213,
        sentiaMANStationTemp214,
        sentiaMANStationTemp215,
        sentiaMANStationTemp216,
        sentiaMANStationTemp217,
        sentiaMANStationTemp218,
        sentiaMANStationTemp219,
        sentiaMANStationTemp220,
        sentiaMANStationTemp221,
        sentiaMANStationTemp222,
        sentiaMANStationTemp223,
        sentiaMANStationTemp224,
        sentiaMANStationTemp225,
        sentiaMANStationTemp226,
        sentiaMANStationTemp227,
        sentiaMANStationTemp228,
        sentiaMANStationTemp229,
        sentiaMANStationTemp230,
        sentiaMANStationTemp231,
        sentiaMANStationTemp232,
        sentiaMANStationTemp301,
        sentiaMANStationTemp302,
        sentiaMANStationTemp303,
        sentiaMANStationTemp304,
        sentiaMANStationTemp305,
        sentiaMANStationTemp306,
        sentiaMANStationTemp307,
        sentiaMANStationTemp308,
        sentiaMANStationTemp309,
        sentiaMANStationTemp310,
        sentiaMANStationTemp311,
        sentiaMANStationTemp312,
        sentiaMANStationTemp313,
        sentiaMANStationTemp314,
        sentiaMANStationTemp315,
        sentiaMANStationTemp316,
        sentiaMANStationTemp317,
        sentiaMANStationTemp318,
        sentiaMANStationTemp319,
        sentiaMANStationTemp320,
        sentiaMANStationTemp321,
        sentiaMANStationTemp322,
        sentiaMANStationTemp323,
        sentiaMANStationTemp324,
        sentiaMANStationTemp325,
        sentiaMANStationTemp326,
        sentiaMANStationTemp327,
        sentiaMANStationTemp328,
        sentiaMANStationTemp329,
        sentiaMANStationTemp330,
        sentiaMANStationTemp331,
        sentiaMANStationTemp332,
        sentiaMANStationHumidity01,
        sentiaMANStationHumidity02,
        sentiaMANStationHumidity03,
        sentiaMANStationHumidity04,
        sentiaMANStationHumidity05,
        sentiaMANStationHumidity06,
        sentiaMANStationHumidity07,
        sentiaMANStationHumidity08,
        sentiaMANStationHumidity09,
        sentiaMANStationHumidity10,
        sentiaMANStationHumidity11,
        sentiaMANStationHumidity12,
        sentiaMANStationHumidity13,
        sentiaMANStationHumidity14,
        sentiaMANStationHumidity15,
        sentiaMANStationHumidity16,
        sentiaMANStationHumidity17,
        sentiaMANStationHumidity18,
        sentiaMANStationHumidity19,
        sentiaMANStationHumidity20,
        sentiaMANStationHumidity21,
        sentiaMANStationHumidity22,
        sentiaMANStationHumidity23,
        sentiaMANStationHumidity24,
        sentiaMANStationHumidity25,
        sentiaMANStationHumidity26,
        sentiaMANStationHumidity27,
        sentiaMANStationHumidity28,
        sentiaMANStationHumidity29,
        sentiaMANStationHumidity30,
        sentiaMANStationHumidity31,
        sentiaMANStationHumidity32,
        sentiaMANStationAlarmState01,
        sentiaMANStationAlarmState02,
        sentiaMANStationAlarmState03,
        sentiaMANStationAlarmState04,
        sentiaMANStationAlarmState05,
        sentiaMANStationAlarmState06,
        sentiaMANStationAlarmState07,
        sentiaMANStationAlarmState08,
        sentiaMANStationAlarmState09,
        sentiaMANStationAlarmState10,
        sentiaMANStationAlarmState11,
        sentiaMANStationAlarmState12,
        sentiaMANStationAlarmState13,
        sentiaMANStationAlarmState14,
        sentiaMANStationAlarmState15,
        sentiaMANStationAlarmState16,
        sentiaMANStationAlarmState17,
        sentiaMANStationAlarmState18,
        sentiaMANStationAlarmState19,
        sentiaMANStationAlarmState20,
        sentiaMANStationAlarmState21,
        sentiaMANStationAlarmState22,
        sentiaMANStationAlarmState23,
        sentiaMANStationAlarmState24,
        sentiaMANStationAlarmState25,
        sentiaMANStationAlarmState26,
        sentiaMANStationAlarmState27,
        sentiaMANStationAlarmState28,
        sentiaMANStationAlarmState29,
        sentiaMANStationAlarmState30,
        sentiaMANStationAlarmState31,
        sentiaMANStationAlarmState32,
        sentiaMANStationLock1State01,
        sentiaMANStationLock1State02,
        sentiaMANStationLock1State03,
        sentiaMANStationLock1State04,
        sentiaMANStationLock1State05,
        sentiaMANStationLock1State06,
        sentiaMANStationLock1State07,
        sentiaMANStationLock1State08,
        sentiaMANStationLock1State09,
        sentiaMANStationLock1State10,
        sentiaMANStationLock1State11,
        sentiaMANStationLock1State12,
        sentiaMANStationLock1State13,
        sentiaMANStationLock1State14,
        sentiaMANStationLock1State15,
        sentiaMANStationLock1State16,
        sentiaMANStationLock1State17,
        sentiaMANStationLock1State18,
        sentiaMANStationLock1State19,
        sentiaMANStationLock1State20,
        sentiaMANStationLock1State21,
        sentiaMANStationLock1State22,
        sentiaMANStationLock1State23,
        sentiaMANStationLock1State24,
        sentiaMANStationLock1State25,
        sentiaMANStationLock1State26,
        sentiaMANStationLock1State27,
        sentiaMANStationLock1State28,
        sentiaMANStationLock1State29,
        sentiaMANStationLock1State30,
        sentiaMANStationLock1State31,
        sentiaMANStationLock1State32,
        sentiaMANStationDoor1State01,
        sentiaMANStationDoor1State02,
        sentiaMANStationDoor1State03,
        sentiaMANStationDoor1State04,
        sentiaMANStationDoor1State05,
        sentiaMANStationDoor1State06,
        sentiaMANStationDoor1State07,
        sentiaMANStationDoor1State08,
        sentiaMANStationDoor1State09,
        sentiaMANStationDoor1State10,
        sentiaMANStationDoor1State11,
        sentiaMANStationDoor1State12,
        sentiaMANStationDoor1State13,
        sentiaMANStationDoor1State14,
        sentiaMANStationDoor1State15,
        sentiaMANStationDoor1State16,
        sentiaMANStationDoor1State17,
        sentiaMANStationDoor1State18,
        sentiaMANStationDoor1State19,
        sentiaMANStationDoor1State20,
        sentiaMANStationDoor1State21,
        sentiaMANStationDoor1State22,
        sentiaMANStationDoor1State23,
        sentiaMANStationDoor1State24,
        sentiaMANStationDoor1State25,
        sentiaMANStationDoor1State26,
        sentiaMANStationDoor1State27,
        sentiaMANStationDoor1State28,
        sentiaMANStationDoor1State29,
        sentiaMANStationDoor1State30,
        sentiaMANStationDoor1State31,
        sentiaMANStationDoor1State32,
        sentiaMANStationLock2State01,
        sentiaMANStationLock2State02,
        sentiaMANStationLock2State03,
        sentiaMANStationLock2State04,
        sentiaMANStationLock2State05,
        sentiaMANStationLock2State06,
        sentiaMANStationLock2State07,
        sentiaMANStationLock2State08,
        sentiaMANStationLock2State09,
        sentiaMANStationLock2State10,
        sentiaMANStationLock2State11,
        sentiaMANStationLock2State12,
        sentiaMANStationLock2State13,
        sentiaMANStationLock2State14,
        sentiaMANStationLock2State15,
        sentiaMANStationLock2State16,
        sentiaMANStationLock2State17,
        sentiaMANStationLock2State18,
        sentiaMANStationLock2State19,
        sentiaMANStationLock2State20,
        sentiaMANStationLock2State21,
        sentiaMANStationLock2State22,
        sentiaMANStationLock2State23,
        sentiaMANStationLock2State24,
        sentiaMANStationLock2State25,
        sentiaMANStationLock2State26,
        sentiaMANStationLock2State27,
        sentiaMANStationLock2State28,
        sentiaMANStationLock2State29,
        sentiaMANStationLock2State30,
        sentiaMANStationLock2State31,
        sentiaMANStationLock2State32,
        sentiaMANStationDoor2State01,
        sentiaMANStationDoor2State02,
        sentiaMANStationDoor2State03,
        sentiaMANStationDoor2State04,
        sentiaMANStationDoor2State05,
        sentiaMANStationDoor2State06,
        sentiaMANStationDoor2State07,
        sentiaMANStationDoor2State08,
        sentiaMANStationDoor2State09,
        sentiaMANStationDoor2State10,
        sentiaMANStationDoor2State11,
        sentiaMANStationDoor2State12,
        sentiaMANStationDoor2State13,
        sentiaMANStationDoor2State14,
        sentiaMANStationDoor2State15,
        sentiaMANStationDoor2State16,
        sentiaMANStationDoor2State17,
        sentiaMANStationDoor2State18,
        sentiaMANStationDoor2State19,
        sentiaMANStationDoor2State20,
        sentiaMANStationDoor2State21,
        sentiaMANStationDoor2State22,
        sentiaMANStationDoor2State23,
        sentiaMANStationDoor2State24,
        sentiaMANStationDoor2State25,
        sentiaMANStationDoor2State26,
        sentiaMANStationDoor2State27,
        sentiaMANStationDoor2State28,
        sentiaMANStationDoor2State29,
        sentiaMANStationDoor2State30,
        sentiaMANStationDoor2State31,
        sentiaMANStationDoor2State32
    }
    STATUS current
    DESCRIPTION
        "sentiaMAN subordinate station objects."
    ::= { strataonGroups 7 }


strataonSentiaPROGroup OBJECT-GROUP
    OBJECTS {
        sentiaPROTemp1,
        sentiaPROTemp2,
        sentiaPROTemp3,
        sentiaPROHumidity,
        sentiaPROAlarmState,
        sentiaPROLock1State,
        sentiaPRODoor1State,
        sentiaPROLock2State,
        sentiaPRODoor2State
    }
    STATUS current
    DESCRIPTION
        "sentiaPRO environmental and access state objects."
    ::= { strataonGroups 8 }


strataonCompliance MODULE-COMPLIANCE
    STATUS current
    DESCRIPTION
        "Base compliance statement for STRATAON SNMP agents."
    MODULE
        MANDATORY-GROUPS {
            strataonSystemGroup,
            strataonNetworkGroup
        }
    ::= { strataonCompliances 1 }

strataonMiniPLCCompliance MODULE-COMPLIANCE
    STATUS current
    DESCRIPTION
        "Compliance statement for STRATAON miniPLC SNMP agents."
    MODULE
        MANDATORY-GROUPS {
            strataonSystemGroup,
            strataonNetworkGroup,
            strataonMiniPLCGroup
        }
    ::= { strataonCompliances 2 }

strataonSmartPDUCompliance MODULE-COMPLIANCE
    STATUS current
    DESCRIPTION
        "Compliance statement for STRATAON smartPDU SNMP agents."
    MODULE
        MANDATORY-GROUPS {
            strataonSystemGroup,
            strataonNetworkGroup,
            strataonSmartPDURelayGroup,
            strataonPduRelayStatsGroup
        }
    ::= { strataonCompliances 3 }

strataonMiniENVCompliance MODULE-COMPLIANCE
    STATUS current
    DESCRIPTION
        "Compliance statement for STRATAON miniENV SNMP agents."
    MODULE
        MANDATORY-GROUPS {
            strataonSystemGroup,
            strataonNetworkGroup,
            strataonMiniENVGroup
        }
    ::= { strataonCompliances 4 }


strataonSentiaMANCompliance MODULE-COMPLIANCE
    STATUS current
    DESCRIPTION
        "Compliance statement for STRATAON sentiaMAN SNMP agents."
    MODULE
        MANDATORY-GROUPS {
            strataonSystemGroup,
            strataonNetworkGroup,
            strataonSentiaMANGroup
        }
    ::= { strataonCompliances 5 }


strataonSentiaPROCompliance MODULE-COMPLIANCE
    STATUS current
    DESCRIPTION
        "Compliance statement for STRATAON sentiaPRO SNMP agents."
    MODULE
        MANDATORY-GROUPS {
            strataonSystemGroup,
            strataonNetworkGroup,
            strataonSentiaPROGroup
        }
    ::= { strataonCompliances 6 }


strataonSentiaLOKGroup OBJECT-GROUP
    OBJECTS {
        sentiaLOKStationCount,
        sentiaLOKStationNode01,
        sentiaLOKStationNode02,
        sentiaLOKStationNode03,
        sentiaLOKStationNode04,
        sentiaLOKStationNode05,
        sentiaLOKStationNode06,
        sentiaLOKStationNode07,
        sentiaLOKStationNode08,
        sentiaLOKStationNode09,
        sentiaLOKStationNode10,
        sentiaLOKStationNode11,
        sentiaLOKStationNode12,
        sentiaLOKStationNode13,
        sentiaLOKStationNode14,
        sentiaLOKStationNode15,
        sentiaLOKStationNode16,
        sentiaLOKStationNode17,
        sentiaLOKStationNode18,
        sentiaLOKStationNode19,
        sentiaLOKStationNode20,
        sentiaLOKStationNode21,
        sentiaLOKStationNode22,
        sentiaLOKStationNode23,
        sentiaLOKStationNode24,
        sentiaLOKStationNode25,
        sentiaLOKStationNode26,
        sentiaLOKStationNode27,
        sentiaLOKStationNode28,
        sentiaLOKStationNode29,
        sentiaLOKStationNode30,
        sentiaLOKStationNode31,
        sentiaLOKStationNode32,
        sentiaLOKStationName01,
        sentiaLOKStationName02,
        sentiaLOKStationName03,
        sentiaLOKStationName04,
        sentiaLOKStationName05,
        sentiaLOKStationName06,
        sentiaLOKStationName07,
        sentiaLOKStationName08,
        sentiaLOKStationName09,
        sentiaLOKStationName10,
        sentiaLOKStationName11,
        sentiaLOKStationName12,
        sentiaLOKStationName13,
        sentiaLOKStationName14,
        sentiaLOKStationName15,
        sentiaLOKStationName16,
        sentiaLOKStationName17,
        sentiaLOKStationName18,
        sentiaLOKStationName19,
        sentiaLOKStationName20,
        sentiaLOKStationName21,
        sentiaLOKStationName22,
        sentiaLOKStationName23,
        sentiaLOKStationName24,
        sentiaLOKStationName25,
        sentiaLOKStationName26,
        sentiaLOKStationName27,
        sentiaLOKStationName28,
        sentiaLOKStationName29,
        sentiaLOKStationName30,
        sentiaLOKStationName31,
        sentiaLOKStationName32,
        sentiaLOKStationCommStatus01,
        sentiaLOKStationCommStatus02,
        sentiaLOKStationCommStatus03,
        sentiaLOKStationCommStatus04,
        sentiaLOKStationCommStatus05,
        sentiaLOKStationCommStatus06,
        sentiaLOKStationCommStatus07,
        sentiaLOKStationCommStatus08,
        sentiaLOKStationCommStatus09,
        sentiaLOKStationCommStatus10,
        sentiaLOKStationCommStatus11,
        sentiaLOKStationCommStatus12,
        sentiaLOKStationCommStatus13,
        sentiaLOKStationCommStatus14,
        sentiaLOKStationCommStatus15,
        sentiaLOKStationCommStatus16,
        sentiaLOKStationCommStatus17,
        sentiaLOKStationCommStatus18,
        sentiaLOKStationCommStatus19,
        sentiaLOKStationCommStatus20,
        sentiaLOKStationCommStatus21,
        sentiaLOKStationCommStatus22,
        sentiaLOKStationCommStatus23,
        sentiaLOKStationCommStatus24,
        sentiaLOKStationCommStatus25,
        sentiaLOKStationCommStatus26,
        sentiaLOKStationCommStatus27,
        sentiaLOKStationCommStatus28,
        sentiaLOKStationCommStatus29,
        sentiaLOKStationCommStatus30,
        sentiaLOKStationCommStatus31,
        sentiaLOKStationCommStatus32,
        sentiaLOKStationFirmware01,
        sentiaLOKStationFirmware02,
        sentiaLOKStationFirmware03,
        sentiaLOKStationFirmware04,
        sentiaLOKStationFirmware05,
        sentiaLOKStationFirmware06,
        sentiaLOKStationFirmware07,
        sentiaLOKStationFirmware08,
        sentiaLOKStationFirmware09,
        sentiaLOKStationFirmware10,
        sentiaLOKStationFirmware11,
        sentiaLOKStationFirmware12,
        sentiaLOKStationFirmware13,
        sentiaLOKStationFirmware14,
        sentiaLOKStationFirmware15,
        sentiaLOKStationFirmware16,
        sentiaLOKStationFirmware17,
        sentiaLOKStationFirmware18,
        sentiaLOKStationFirmware19,
        sentiaLOKStationFirmware20,
        sentiaLOKStationFirmware21,
        sentiaLOKStationFirmware22,
        sentiaLOKStationFirmware23,
        sentiaLOKStationFirmware24,
        sentiaLOKStationFirmware25,
        sentiaLOKStationFirmware26,
        sentiaLOKStationFirmware27,
        sentiaLOKStationFirmware28,
        sentiaLOKStationFirmware29,
        sentiaLOKStationFirmware30,
        sentiaLOKStationFirmware31,
        sentiaLOKStationFirmware32,
        sentiaLOKStationDeviceType01,
        sentiaLOKStationDeviceType02,
        sentiaLOKStationDeviceType03,
        sentiaLOKStationDeviceType04,
        sentiaLOKStationDeviceType05,
        sentiaLOKStationDeviceType06,
        sentiaLOKStationDeviceType07,
        sentiaLOKStationDeviceType08,
        sentiaLOKStationDeviceType09,
        sentiaLOKStationDeviceType10,
        sentiaLOKStationDeviceType11,
        sentiaLOKStationDeviceType12,
        sentiaLOKStationDeviceType13,
        sentiaLOKStationDeviceType14,
        sentiaLOKStationDeviceType15,
        sentiaLOKStationDeviceType16,
        sentiaLOKStationDeviceType17,
        sentiaLOKStationDeviceType18,
        sentiaLOKStationDeviceType19,
        sentiaLOKStationDeviceType20,
        sentiaLOKStationDeviceType21,
        sentiaLOKStationDeviceType22,
        sentiaLOKStationDeviceType23,
        sentiaLOKStationDeviceType24,
        sentiaLOKStationDeviceType25,
        sentiaLOKStationDeviceType26,
        sentiaLOKStationDeviceType27,
        sentiaLOKStationDeviceType28,
        sentiaLOKStationDeviceType29,
        sentiaLOKStationDeviceType30,
        sentiaLOKStationDeviceType31,
        sentiaLOKStationDeviceType32,
        sentiaLOKInput01State01,
        sentiaLOKInput01State02,
        sentiaLOKInput01State03,
        sentiaLOKInput01State04,
        sentiaLOKInput01State05,
        sentiaLOKInput01State06,
        sentiaLOKInput01State07,
        sentiaLOKInput01State08,
        sentiaLOKInput01State09,
        sentiaLOKInput01State10,
        sentiaLOKInput01State11,
        sentiaLOKInput01State12,
        sentiaLOKInput01State13,
        sentiaLOKInput01State14,
        sentiaLOKInput01State15,
        sentiaLOKInput01State16,
        sentiaLOKInput01State17,
        sentiaLOKInput01State18,
        sentiaLOKInput01State19,
        sentiaLOKInput01State20,
        sentiaLOKInput01State21,
        sentiaLOKInput01State22,
        sentiaLOKInput01State23,
        sentiaLOKInput01State24,
        sentiaLOKInput01State25,
        sentiaLOKInput01State26,
        sentiaLOKInput01State27,
        sentiaLOKInput01State28,
        sentiaLOKInput01State29,
        sentiaLOKInput01State30,
        sentiaLOKInput01State31,
        sentiaLOKInput01State32,
        sentiaLOKInput02State01,
        sentiaLOKInput02State02,
        sentiaLOKInput02State03,
        sentiaLOKInput02State04,
        sentiaLOKInput02State05,
        sentiaLOKInput02State06,
        sentiaLOKInput02State07,
        sentiaLOKInput02State08,
        sentiaLOKInput02State09,
        sentiaLOKInput02State10,
        sentiaLOKInput02State11,
        sentiaLOKInput02State12,
        sentiaLOKInput02State13,
        sentiaLOKInput02State14,
        sentiaLOKInput02State15,
        sentiaLOKInput02State16,
        sentiaLOKInput02State17,
        sentiaLOKInput02State18,
        sentiaLOKInput02State19,
        sentiaLOKInput02State20,
        sentiaLOKInput02State21,
        sentiaLOKInput02State22,
        sentiaLOKInput02State23,
        sentiaLOKInput02State24,
        sentiaLOKInput02State25,
        sentiaLOKInput02State26,
        sentiaLOKInput02State27,
        sentiaLOKInput02State28,
        sentiaLOKInput02State29,
        sentiaLOKInput02State30,
        sentiaLOKInput02State31,
        sentiaLOKInput02State32,
        sentiaLOKInput03State01,
        sentiaLOKInput03State02,
        sentiaLOKInput03State03,
        sentiaLOKInput03State04,
        sentiaLOKInput03State05,
        sentiaLOKInput03State06,
        sentiaLOKInput03State07,
        sentiaLOKInput03State08,
        sentiaLOKInput03State09,
        sentiaLOKInput03State10,
        sentiaLOKInput03State11,
        sentiaLOKInput03State12,
        sentiaLOKInput03State13,
        sentiaLOKInput03State14,
        sentiaLOKInput03State15,
        sentiaLOKInput03State16,
        sentiaLOKInput03State17,
        sentiaLOKInput03State18,
        sentiaLOKInput03State19,
        sentiaLOKInput03State20,
        sentiaLOKInput03State21,
        sentiaLOKInput03State22,
        sentiaLOKInput03State23,
        sentiaLOKInput03State24,
        sentiaLOKInput03State25,
        sentiaLOKInput03State26,
        sentiaLOKInput03State27,
        sentiaLOKInput03State28,
        sentiaLOKInput03State29,
        sentiaLOKInput03State30,
        sentiaLOKInput03State31,
        sentiaLOKInput03State32,
        sentiaLOKInput04State01,
        sentiaLOKInput04State02,
        sentiaLOKInput04State03,
        sentiaLOKInput04State04,
        sentiaLOKInput04State05,
        sentiaLOKInput04State06,
        sentiaLOKInput04State07,
        sentiaLOKInput04State08,
        sentiaLOKInput04State09,
        sentiaLOKInput04State10,
        sentiaLOKInput04State11,
        sentiaLOKInput04State12,
        sentiaLOKInput04State13,
        sentiaLOKInput04State14,
        sentiaLOKInput04State15,
        sentiaLOKInput04State16,
        sentiaLOKInput04State17,
        sentiaLOKInput04State18,
        sentiaLOKInput04State19,
        sentiaLOKInput04State20,
        sentiaLOKInput04State21,
        sentiaLOKInput04State22,
        sentiaLOKInput04State23,
        sentiaLOKInput04State24,
        sentiaLOKInput04State25,
        sentiaLOKInput04State26,
        sentiaLOKInput04State27,
        sentiaLOKInput04State28,
        sentiaLOKInput04State29,
        sentiaLOKInput04State30,
        sentiaLOKInput04State31,
        sentiaLOKInput04State32,
        sentiaLOKInput05State01,
        sentiaLOKInput05State02,
        sentiaLOKInput05State03,
        sentiaLOKInput05State04,
        sentiaLOKInput05State05,
        sentiaLOKInput05State06,
        sentiaLOKInput05State07,
        sentiaLOKInput05State08,
        sentiaLOKInput05State09,
        sentiaLOKInput05State10,
        sentiaLOKInput05State11,
        sentiaLOKInput05State12,
        sentiaLOKInput05State13,
        sentiaLOKInput05State14,
        sentiaLOKInput05State15,
        sentiaLOKInput05State16,
        sentiaLOKInput05State17,
        sentiaLOKInput05State18,
        sentiaLOKInput05State19,
        sentiaLOKInput05State20,
        sentiaLOKInput05State21,
        sentiaLOKInput05State22,
        sentiaLOKInput05State23,
        sentiaLOKInput05State24,
        sentiaLOKInput05State25,
        sentiaLOKInput05State26,
        sentiaLOKInput05State27,
        sentiaLOKInput05State28,
        sentiaLOKInput05State29,
        sentiaLOKInput05State30,
        sentiaLOKInput05State31,
        sentiaLOKInput05State32,
        sentiaLOKInput06State01,
        sentiaLOKInput06State02,
        sentiaLOKInput06State03,
        sentiaLOKInput06State04,
        sentiaLOKInput06State05,
        sentiaLOKInput06State06,
        sentiaLOKInput06State07,
        sentiaLOKInput06State08,
        sentiaLOKInput06State09,
        sentiaLOKInput06State10,
        sentiaLOKInput06State11,
        sentiaLOKInput06State12,
        sentiaLOKInput06State13,
        sentiaLOKInput06State14,
        sentiaLOKInput06State15,
        sentiaLOKInput06State16,
        sentiaLOKInput06State17,
        sentiaLOKInput06State18,
        sentiaLOKInput06State19,
        sentiaLOKInput06State20,
        sentiaLOKInput06State21,
        sentiaLOKInput06State22,
        sentiaLOKInput06State23,
        sentiaLOKInput06State24,
        sentiaLOKInput06State25,
        sentiaLOKInput06State26,
        sentiaLOKInput06State27,
        sentiaLOKInput06State28,
        sentiaLOKInput06State29,
        sentiaLOKInput06State30,
        sentiaLOKInput06State31,
        sentiaLOKInput06State32,
        sentiaLOKInput07State01,
        sentiaLOKInput07State02,
        sentiaLOKInput07State03,
        sentiaLOKInput07State04,
        sentiaLOKInput07State05,
        sentiaLOKInput07State06,
        sentiaLOKInput07State07,
        sentiaLOKInput07State08,
        sentiaLOKInput07State09,
        sentiaLOKInput07State10,
        sentiaLOKInput07State11,
        sentiaLOKInput07State12,
        sentiaLOKInput07State13,
        sentiaLOKInput07State14,
        sentiaLOKInput07State15,
        sentiaLOKInput07State16,
        sentiaLOKInput07State17,
        sentiaLOKInput07State18,
        sentiaLOKInput07State19,
        sentiaLOKInput07State20,
        sentiaLOKInput07State21,
        sentiaLOKInput07State22,
        sentiaLOKInput07State23,
        sentiaLOKInput07State24,
        sentiaLOKInput07State25,
        sentiaLOKInput07State26,
        sentiaLOKInput07State27,
        sentiaLOKInput07State28,
        sentiaLOKInput07State29,
        sentiaLOKInput07State30,
        sentiaLOKInput07State31,
        sentiaLOKInput07State32,
        sentiaLOKInput08State01,
        sentiaLOKInput08State02,
        sentiaLOKInput08State03,
        sentiaLOKInput08State04,
        sentiaLOKInput08State05,
        sentiaLOKInput08State06,
        sentiaLOKInput08State07,
        sentiaLOKInput08State08,
        sentiaLOKInput08State09,
        sentiaLOKInput08State10,
        sentiaLOKInput08State11,
        sentiaLOKInput08State12,
        sentiaLOKInput08State13,
        sentiaLOKInput08State14,
        sentiaLOKInput08State15,
        sentiaLOKInput08State16,
        sentiaLOKInput08State17,
        sentiaLOKInput08State18,
        sentiaLOKInput08State19,
        sentiaLOKInput08State20,
        sentiaLOKInput08State21,
        sentiaLOKInput08State22,
        sentiaLOKInput08State23,
        sentiaLOKInput08State24,
        sentiaLOKInput08State25,
        sentiaLOKInput08State26,
        sentiaLOKInput08State27,
        sentiaLOKInput08State28,
        sentiaLOKInput08State29,
        sentiaLOKInput08State30,
        sentiaLOKInput08State31,
        sentiaLOKInput08State32,
        sentiaLOKOutput01State01,
        sentiaLOKOutput01State02,
        sentiaLOKOutput01State03,
        sentiaLOKOutput01State04,
        sentiaLOKOutput01State05,
        sentiaLOKOutput01State06,
        sentiaLOKOutput01State07,
        sentiaLOKOutput01State08,
        sentiaLOKOutput01State09,
        sentiaLOKOutput01State10,
        sentiaLOKOutput01State11,
        sentiaLOKOutput01State12,
        sentiaLOKOutput01State13,
        sentiaLOKOutput01State14,
        sentiaLOKOutput01State15,
        sentiaLOKOutput01State16,
        sentiaLOKOutput01State17,
        sentiaLOKOutput01State18,
        sentiaLOKOutput01State19,
        sentiaLOKOutput01State20,
        sentiaLOKOutput01State21,
        sentiaLOKOutput01State22,
        sentiaLOKOutput01State23,
        sentiaLOKOutput01State24,
        sentiaLOKOutput01State25,
        sentiaLOKOutput01State26,
        sentiaLOKOutput01State27,
        sentiaLOKOutput01State28,
        sentiaLOKOutput01State29,
        sentiaLOKOutput01State30,
        sentiaLOKOutput01State31,
        sentiaLOKOutput01State32,
        sentiaLOKOutput02State01,
        sentiaLOKOutput02State02,
        sentiaLOKOutput02State03,
        sentiaLOKOutput02State04,
        sentiaLOKOutput02State05,
        sentiaLOKOutput02State06,
        sentiaLOKOutput02State07,
        sentiaLOKOutput02State08,
        sentiaLOKOutput02State09,
        sentiaLOKOutput02State10,
        sentiaLOKOutput02State11,
        sentiaLOKOutput02State12,
        sentiaLOKOutput02State13,
        sentiaLOKOutput02State14,
        sentiaLOKOutput02State15,
        sentiaLOKOutput02State16,
        sentiaLOKOutput02State17,
        sentiaLOKOutput02State18,
        sentiaLOKOutput02State19,
        sentiaLOKOutput02State20,
        sentiaLOKOutput02State21,
        sentiaLOKOutput02State22,
        sentiaLOKOutput02State23,
        sentiaLOKOutput02State24,
        sentiaLOKOutput02State25,
        sentiaLOKOutput02State26,
        sentiaLOKOutput02State27,
        sentiaLOKOutput02State28,
        sentiaLOKOutput02State29,
        sentiaLOKOutput02State30,
        sentiaLOKOutput02State31,
        sentiaLOKOutput02State32,
        sentiaLOKOutput03State01,
        sentiaLOKOutput03State02,
        sentiaLOKOutput03State03,
        sentiaLOKOutput03State04,
        sentiaLOKOutput03State05,
        sentiaLOKOutput03State06,
        sentiaLOKOutput03State07,
        sentiaLOKOutput03State08,
        sentiaLOKOutput03State09,
        sentiaLOKOutput03State10,
        sentiaLOKOutput03State11,
        sentiaLOKOutput03State12,
        sentiaLOKOutput03State13,
        sentiaLOKOutput03State14,
        sentiaLOKOutput03State15,
        sentiaLOKOutput03State16,
        sentiaLOKOutput03State17,
        sentiaLOKOutput03State18,
        sentiaLOKOutput03State19,
        sentiaLOKOutput03State20,
        sentiaLOKOutput03State21,
        sentiaLOKOutput03State22,
        sentiaLOKOutput03State23,
        sentiaLOKOutput03State24,
        sentiaLOKOutput03State25,
        sentiaLOKOutput03State26,
        sentiaLOKOutput03State27,
        sentiaLOKOutput03State28,
        sentiaLOKOutput03State29,
        sentiaLOKOutput03State30,
        sentiaLOKOutput03State31,
        sentiaLOKOutput03State32,
        sentiaLOKOutput04State01,
        sentiaLOKOutput04State02,
        sentiaLOKOutput04State03,
        sentiaLOKOutput04State04,
        sentiaLOKOutput04State05,
        sentiaLOKOutput04State06,
        sentiaLOKOutput04State07,
        sentiaLOKOutput04State08,
        sentiaLOKOutput04State09,
        sentiaLOKOutput04State10,
        sentiaLOKOutput04State11,
        sentiaLOKOutput04State12,
        sentiaLOKOutput04State13,
        sentiaLOKOutput04State14,
        sentiaLOKOutput04State15,
        sentiaLOKOutput04State16,
        sentiaLOKOutput04State17,
        sentiaLOKOutput04State18,
        sentiaLOKOutput04State19,
        sentiaLOKOutput04State20,
        sentiaLOKOutput04State21,
        sentiaLOKOutput04State22,
        sentiaLOKOutput04State23,
        sentiaLOKOutput04State24,
        sentiaLOKOutput04State25,
        sentiaLOKOutput04State26,
        sentiaLOKOutput04State27,
        sentiaLOKOutput04State28,
        sentiaLOKOutput04State29,
        sentiaLOKOutput04State30,
        sentiaLOKOutput04State31,
        sentiaLOKOutput04State32,
        sentiaLOKOutput05State01,
        sentiaLOKOutput05State02,
        sentiaLOKOutput05State03,
        sentiaLOKOutput05State04,
        sentiaLOKOutput05State05,
        sentiaLOKOutput05State06,
        sentiaLOKOutput05State07,
        sentiaLOKOutput05State08,
        sentiaLOKOutput05State09,
        sentiaLOKOutput05State10,
        sentiaLOKOutput05State11,
        sentiaLOKOutput05State12,
        sentiaLOKOutput05State13,
        sentiaLOKOutput05State14,
        sentiaLOKOutput05State15,
        sentiaLOKOutput05State16,
        sentiaLOKOutput05State17,
        sentiaLOKOutput05State18,
        sentiaLOKOutput05State19,
        sentiaLOKOutput05State20,
        sentiaLOKOutput05State21,
        sentiaLOKOutput05State22,
        sentiaLOKOutput05State23,
        sentiaLOKOutput05State24,
        sentiaLOKOutput05State25,
        sentiaLOKOutput05State26,
        sentiaLOKOutput05State27,
        sentiaLOKOutput05State28,
        sentiaLOKOutput05State29,
        sentiaLOKOutput05State30,
        sentiaLOKOutput05State31,
        sentiaLOKOutput05State32,
        sentiaLOKOutput06State01,
        sentiaLOKOutput06State02,
        sentiaLOKOutput06State03,
        sentiaLOKOutput06State04,
        sentiaLOKOutput06State05,
        sentiaLOKOutput06State06,
        sentiaLOKOutput06State07,
        sentiaLOKOutput06State08,
        sentiaLOKOutput06State09,
        sentiaLOKOutput06State10,
        sentiaLOKOutput06State11,
        sentiaLOKOutput06State12,
        sentiaLOKOutput06State13,
        sentiaLOKOutput06State14,
        sentiaLOKOutput06State15,
        sentiaLOKOutput06State16,
        sentiaLOKOutput06State17,
        sentiaLOKOutput06State18,
        sentiaLOKOutput06State19,
        sentiaLOKOutput06State20,
        sentiaLOKOutput06State21,
        sentiaLOKOutput06State22,
        sentiaLOKOutput06State23,
        sentiaLOKOutput06State24,
        sentiaLOKOutput06State25,
        sentiaLOKOutput06State26,
        sentiaLOKOutput06State27,
        sentiaLOKOutput06State28,
        sentiaLOKOutput06State29,
        sentiaLOKOutput06State30,
        sentiaLOKOutput06State31,
        sentiaLOKOutput06State32,
        sentiaLOKOutput07State01,
        sentiaLOKOutput07State02,
        sentiaLOKOutput07State03,
        sentiaLOKOutput07State04,
        sentiaLOKOutput07State05,
        sentiaLOKOutput07State06,
        sentiaLOKOutput07State07,
        sentiaLOKOutput07State08,
        sentiaLOKOutput07State09,
        sentiaLOKOutput07State10,
        sentiaLOKOutput07State11,
        sentiaLOKOutput07State12,
        sentiaLOKOutput07State13,
        sentiaLOKOutput07State14,
        sentiaLOKOutput07State15,
        sentiaLOKOutput07State16,
        sentiaLOKOutput07State17,
        sentiaLOKOutput07State18,
        sentiaLOKOutput07State19,
        sentiaLOKOutput07State20,
        sentiaLOKOutput07State21,
        sentiaLOKOutput07State22,
        sentiaLOKOutput07State23,
        sentiaLOKOutput07State24,
        sentiaLOKOutput07State25,
        sentiaLOKOutput07State26,
        sentiaLOKOutput07State27,
        sentiaLOKOutput07State28,
        sentiaLOKOutput07State29,
        sentiaLOKOutput07State30,
        sentiaLOKOutput07State31,
        sentiaLOKOutput07State32,
        sentiaLOKOutput08State01,
        sentiaLOKOutput08State02,
        sentiaLOKOutput08State03,
        sentiaLOKOutput08State04,
        sentiaLOKOutput08State05,
        sentiaLOKOutput08State06,
        sentiaLOKOutput08State07,
        sentiaLOKOutput08State08,
        sentiaLOKOutput08State09,
        sentiaLOKOutput08State10,
        sentiaLOKOutput08State11,
        sentiaLOKOutput08State12,
        sentiaLOKOutput08State13,
        sentiaLOKOutput08State14,
        sentiaLOKOutput08State15,
        sentiaLOKOutput08State16,
        sentiaLOKOutput08State17,
        sentiaLOKOutput08State18,
        sentiaLOKOutput08State19,
        sentiaLOKOutput08State20,
        sentiaLOKOutput08State21,
        sentiaLOKOutput08State22,
        sentiaLOKOutput08State23,
        sentiaLOKOutput08State24,
        sentiaLOKOutput08State25,
        sentiaLOKOutput08State26,
        sentiaLOKOutput08State27,
        sentiaLOKOutput08State28,
        sentiaLOKOutput08State29,
        sentiaLOKOutput08State30,
        sentiaLOKOutput08State31,
        sentiaLOKOutput08State32
    }
    STATUS current
    DESCRIPTION "sentiaLOK subordinate station objects."
    ::= { strataonGroups 9 }

strataonSentiaLOKCompliance MODULE-COMPLIANCE
    STATUS current
    DESCRIPTION "Compliance statement for STRATAON sentiaLOK SNMP agents."
    MODULE
        MANDATORY-GROUPS { strataonSystemGroup, strataonNetworkGroup, strataonSentiaLOKGroup }
    ::= { strataonCompliances 7 }

END
